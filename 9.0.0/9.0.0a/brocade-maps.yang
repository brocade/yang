module brocade-maps {

    yang-version 1.1;
    namespace "urn:brocade.com:mgmt:brocade-maps";
    prefix brocade-maps;
    
    import brocade-maps-types {
        prefix maps-types;
    }
    import ietf-inet-types {
        prefix inet;
    }
    import ietf-yang-types {
        prefix yang;
    }

   import fibrechannel-yang-types {
        prefix fibrechannel;
   }
   organization
    "Broadcom Inc.";

    contact
    "
    Address:

      1320 Ridder Park Road
      San Jose, CA 95131
      USA

    Support:

      https://www.broadcom.com/support/fibre-channel-networking/

    Website:

      https://www.broadcom.com/products/fibre-channel-networking/software/

    ";

    description
    "
    Copyright © 2019 Broadcom. All rights reserved. The term 'Broadcom' refers
    to Broadcom Inc. and/or its subsidiaries.
    ";

    revision 2019-12-13 {
      description
      "
      FOS 9.0.0
      ---------
      Removed ssp-state-type and maps-group-feature-type types
      Added dashboard-history
      Platform specific information has been removed from decommission-cfg node
      Fixed the leaf nodes having self reference

      Fabric OS 8.2.1b
      -----
      Refine descriptions.
      
      FOS 8.2.1
      -----
      Initial release.
      Refine descriptions.
      ";
        reference
          "
          Brocade Monitoring and Alerting Policy Suite Configuration Guide
          ";
  }
    

  container brocade-maps {

    description 
      "
      The manageable MAPS features.
      ";
      
    container switch-status-policy-report {
      config false;
      description 
        "
        The Switch Status Policy (SSP) report. The SSP report provides the 
        overall health status of the switch and includes enough information for
        you to investigate further, if necessary.
        ";


      leaf switch-health {
        type maps-types:ssp-state-type;
        description 
          "
          The overall status of the switch. The switch state is determined by 
          the state of one or more of its components.
          ";
        }
      leaf power-supply-health {
        type maps-types:ssp-state-type;
        description
          "
          The state of the power supplies. 
          ";
        }
        
      leaf fan-health {
        type maps-types:ssp-state-type;
        description
          "
          The state of the fans. 
          ";
        }
        
      leaf wwn-health {
        if-feature fibrechannel:fibrechannel_chassis_platform;
        type maps-types:ssp-state-type;
        description 
          "
          The state of the WWN cards. 
          ";
        }
        
      leaf temperature-sensor-health {
        type maps-types:ssp-state-type;
        description
          "
          The state of the temperature sensors. 
          ";
        }
        
      leaf ha-health {
        if-feature fibrechannel:fibrechannel_chassis_platform;
        type maps-types:ssp-state-type;
        description
          "
          The state of the high availability state (both control processors 
          are in sync).
          ";
      }
      leaf control-processor-health {
        if-feature fibrechannel:fibrechannel_chassis_platform;
        type maps-types:ssp-state-type;
        description
          "
          The  state of the control processors.
          ";
      }
      leaf core-blade-health {
        if-feature fibrechannel:fibrechannel_chassis_platform;
        type maps-types:ssp-state-type;
        description 
          "
          The state of the core blades. 
          ";
      }
      leaf blade-health {
        if-feature fibrechannel:fibrechannel_chassis_platform;
        type maps-types:ssp-state-type;
        description 
          "
          The state of the application blades.
          ";
      }
      leaf flash-health {
        type maps-types:ssp-state-type;
        description
          "
          The state of the flash usage. Flash usage could be above the
          threshold or limit.
          ";
      }
      leaf marginal-port-health {
        type maps-types:ssp-state-type;
        description 
          "
          The state of the marginal ports. 
          ";
      }
      leaf faulty-port-health {
        type maps-types:ssp-state-type;
        description
          "
          The state of the faulty ports.
          ";
      }
      leaf missing-sfp-health {
        type maps-types:ssp-state-type;
        description
          "
          The state of the missing SFPs.
          ";
      }
      leaf error-port-health {
        type maps-types:ssp-state-type;
        description
          "
          The state of the error ports.
          ";
      }
      leaf expired-certificate-health {
        type maps-types:ssp-state-type;
        description
          "
          The state of the expired certificate.
          ";
      }
      leaf airflow-mismatch-health {
        type maps-types:ssp-state-type;
        description
          "
          The state of the air flow. This parameter monitors the air flow 
          direction of the power supply fan FRUs and blower FRUs and generates 
          an alert if there is a mismatch in the air flow direction of any two 
          power supply fans or any two blowers.
          ";
      }
      leaf marginal-sfp-health {
        type maps-types:ssp-state-type;
        description
          "
          The state of SFPs. If a certain percentage of SFPs are in SFP_MARGINAL
          then, the switch state is moved to marginal or down.
          ";
      }
      leaf trusted-fos-certificate-health {
        type maps-types:ssp-state-type;
        description
          "
          trusted FOS certificate state, the switch state is moved to marginal
          or down when the certificate gets expired.
          ";
      }
    }
    container system-resources {
      config false;
      description 
        "
        The system resources (such as CPU, RAM, and flash memory usage). 
        Note that usage is not real time and may be delayed up to 2 minutes.
        ";
        
      leaf cpu-usage {
        type uint32 {
          range "0 .. 100";
        }
        units "percentage";
        description 
          "
          The percentage of CPU usage.
          ";
      }
      leaf memory-usage {
        type uint32 {
          range "0 .. 100";
        }
        units "percentage";
        description
          "
          The percentage of memory usage. 
          ";
      }
      leaf total-memory {
        type uint32 {
          range "0 .. max";
        }
        units "kilobytes";
        description
          "
          The total memory usage.
          ";
      }
      leaf flash-usage {
        type uint32 {
          range "0 .. 100";
        }
        units "percentage";
        description
        "
        The percentage of flash usage. 
        ";
      }
    }
    
    list paused-cfg {
      key "group-type";
      description
        "
        A list of elements or element groups that you want to pause
        or restart with monitoring. You can only pause or restart
        monitoring of FC ports, FCIP circuits (and QOS), SFPs and
        switch groups. All the supported groups can be paused or
        restarted with monitoring using keyword all.
        ";
        
        leaf group-type {
          type enumeration {
            enum "fc-port" {
              description
                "
                The FC port group type. This group manages the FC ports.
                ";
            }
            enum "sfp" {
              description
                "
                The FC SFP group type. This group manages the FC SFPs.
                The system can have different SFPs based on speed or vendor.
                ";
            }
            enum "circuit" {
              description
                "
                The circuit group type. This group manages circuits.
                A circuit is a virtual connection between two extension systems.
                ";
            }
            enum "switch" {
              description
                "
                The switch group type. This group manages the Switch.
                ";
            }
            enum "all" {
              description
                "
                The Keyword all represents the supported group types for
		pause and continue feature.
                ";
            }
          }
          description
            "
            The element group of which you want to pause or restart monitoring.
            ";
        }
        container members {
          when "../group-type != all and ../group-type != switch";
          description
            "
            A list of elements (ports, FCIP circuits, SFPs, Switch).
            There must be at least one member in the list.
            Members can take special input all, which indicates all the above
            mentioned group types.
            ";
          leaf-list member {
            type string {
              length "0..100";
              pattern "[a-z,' ']*([0-9]{1,3})*|-|,|/";
            }
            min-elements 1;
            description
              "
              An element (port, FCIP circuit, SFP, Switch or all).
              ";
          }
        }
    }

    list group {
      key "name";
      description
        "
        A list of groups to be monitored using the same set of thresholds. 
        For example, you can create a group of ports that behave in a similar 
        manner, such as UNIX ports or long-distance ports. Note that all 
        elements (ports, FCIP circuits, or SFPs) in a group must be of the same 
        type. By creating a group of similar elements, you can manage these 
        elements as a single entity. 
        You can create up to 64 user-defined groups per logical switch.
        ";
      leaf name {
       type maps-types:maps-group-name-type;
       description
         "
         The group name.
         ";
      }
      leaf group-type {
       type maps-types:maps-group-type-type;
       mandatory true;
       description
         "
         The group type.
         ";
      }
      leaf group-feature {
       type maps-types:maps-group-feature-type;
       description
         "
         The group feature.
         ";
      }
      leaf feature-pattern {
       when "../group-feature = node-wwn or ../group-feature = port-name";
       type string {
         length "0..32";
         pattern "!|[a-zA-Z0-9?,_,-,:,*]*";
       }
       description
         "
         The feature pattern.
         ";
      }
      leaf is-predefined {
       type boolean;
       config false;
       description
         "
         Whether the group is a system-defined or user-defined group. You 
         cannot delete system-defined groups; however, you can augment the 
         ports managed by the group.
         
         true : The group is system-defined. 
         false: The group is user-defined.
         ";
      }
      leaf is-modifiable {
       type boolean;
       config false;
       description
         "
         Whether you can modify the group.
         true : The system-defined group can be modified. 
         false: The system-defined group cannot be modified. 
         ";
      }
      container members {
       when "../group-feature != node-wwn and ../group-feature != port-name";
       description
         "
         A list of members (such as, node-wwn or port-name).
         ";
       leaf-list member {
         type string {
           length "0..100";
           pattern "[a-z,' ']*([0-9]{1,3})*|-|,|/";
         }
         description
           "
           A member (such as, node-wwn or port-name).
           ";
        }
      }
    }
    
    container maps-config {
      description
        "
        The MAPS configuration for the switch. You can perform the following 
        MAPS configurations using this container:
        1. View the current MAPS configuration.
        2. Define the actions to take on the switch when a threshold is 
           triggered.
        3. Specify the e-mail addresses to which the alerts are sent.
        4. Delete all user-defined MAPS configurations related to rules, groups,
           policies, and so on.
        ";
        
      container actions {
        description
          "
          The global MAPS actions list.
          ";
        leaf-list action {
          type maps-types:maps-generic-action-type;
          description
            "
            The MAPS actions. You can enable one or more actions globally at 
            the switch level or per rule. 
            ";
        }
      }
      leaf decommission-cfg {
        type enumeration {
          enum "impair" {
            description
              "
              The decommission behavior is to impair the link. After 
              this action triggers, the port remains online with no routes
              unless no other shortest path links exist.
              ";
          }
          enum "with-disable" {
            description
              "
              The decommission behavior is to decommission and disable the 
              port (or fence if the process fails).
              ";
            }
          }
          description
            "
            The decommission behavior (with-disable or impair).
            ";
      }
      container recipient-address-list {
        description
          "
          The recipient list for e-mail alerts.
          ";
        leaf-list recipient-address {
          type string {
            length "5..128";
            pattern "[0-9a-zA-Z@_.]*";
          }
          max-elements 5;
          description 
            "
            The e-mail address (such as john@mmm.com or psingh@xyz.com) for
            recipients of e-mail alerts.
            ";
        }
      }

      leaf sender-address {
        type string {
          length "5..128";
          pattern "[0-9a-zA-Z@_.]*";
        }
        description 
          "
          The e-mail address of the sender.
          ";
      }
      leaf domain-name {
        type string {
          length "4..63";
          pattern "([a-zA-Z]{0,1}[0-9a-zA-Z_]{2,3}[0-9a-zA-Z_]{4,63})";
        }
        description 
        "
        The domain name. Enter none to clear the name.
        ";
      }
      leaf relay-ip-address {
        type inet:ip-address;
        description 
          "
          The relay IP address. Enter none to clear the IP address.
          ";
      }
      leaf quiet-time {
        type uint32 {
          range "0..720";
        }
        units "hours";
        description
          "
          The global quiet time. Rules in the policy will not be triggered
          until quiet time has expired..
          ";
      }
      container test-email {
        description
          "
          The test email.
          ";
        leaf subject {
        type string {
          length "0..256";
          pattern "[ -~]";
        }
        description
          "
          The subject for the email alert.
          ";
        }
        leaf body {
          type string {
            length "0..512";
            pattern "[ -~]";   
        }
          description
            "
            The message for the email alert.
            ";
          }
      }
      leaf f-port-fpi-profile {
        type maps-types:maps-policy-name-type;
        description 
          "
          The F-Port FPI active profile name.
          ";
      }
      leaf e-port-fpi-profile {
        type maps-types:maps-policy-name-type;
        description 
          "
          The E-Port FPI active profile name.
          ";
      }
    }
    list dashboard-rule {
        config false;
        description
          "
          A list of dashboards. The dashboard enables you to view the events or 
          rules triggered and the objects on which the rules were triggered over
          a specified period of time You can also clear the dashboard data. 
          
          You can view a triggered rules list for the last 7 days. You need the 
          rule list to get the complete picture of switch operation. 
          The dashboard data provides two views of the operating state - 
          the state since midnight and the state for the last 7 days.
          For both the views, you need to complete details of each rule 
          triggered and all of the rule data.
          There are several logical categories to classify the rules and each
          category can have maximum 5 rules per hour and the rule can have
          maximum 5 objects.
          ";

        leaf category {
          type maps-types:maps-dashboard-category-type;
          description
            "
            The dashboard category. Each rule can belong to only one category.
            ";
        }
        leaf name {
          type maps-types:maps-rule-name-type;
          description 
            "
            The rule name.
            ";
        }
        leaf triggered-count {
          type uint32 {
            range "0..max";
          }
          description 
            "
            The number of times the rule was triggered for the category.
            ";
        }
        leaf time-stamp {
          type yang:date-and-time;
          description 
            "
            The date and time that the rule was last triggered.
            ";
        }
        leaf repetition-count {
          type uint32 {
            range "0..max";
          }
          description 
            "
            The number of times a rule was triggered. The same rule can be 
            triggered multiple times for the same or different objects. 
            For example, if the defALL_D_PORTSCRC_10 rule is triggered 20 times 
            in an hour for different objects, then the repetition-count is 20.
            ";
        }
        container objects {
          description 
            "
            The objects that violated the rule. For example port, circuit.
            ";
          leaf-list object {
            type string {
              pattern "[0-9a-fA-F,/]*";
            }
            description
              "
              The object that violated the rule. For example, port, circuit, 
              and so on. The object format is as follows: <element>:<value>. 
              For example, 'F-Port 10:90' and 'U-Port 11:11'. Element can
              port with type, power supply, chassis etc.
              Maximum five objects can be present in one rule entry of
              dashboard. 
              ";
          }
        }
    }
    
    container dashboard-misc {
      description
        "
        The dashboard miscellaneous information (such as start time 
        and operation).
        ";
      
      leaf maps-start-time {
        type yang:date-and-time;
        config false;
        description
          "
          The MAPS start time. MAPS is restartable service which means the 
          start time could be different than system up time.
          ";
        }
        leaf clear-data {
          type boolean;
          default "true";
          description
            "
            Whether to clear the dashboard data.
            true : Clears the dashboard data. 
            false: Does not clear the dashboard data.
            NOTE: write-only leaf node and would not be present in GET request.
            ";
        }
    }

    list credit-stall-dashboard {
      config false;
      description
        "
        The dashboard congestion credit-stall provides information about the
        monitored ports.
        ";

       leaf slot-port {
         type fibrechannel:slot-port-name-type;
         description
           "
	   Specifies slot and port information in slot/port format.
           ";
       }
       leaf timestamp {
         type yang:date-and-time;
         description
           "
	   Specifies system time of credit-stall congestion data sample.
	   The congestion data sample is available per minute and it is
	   arranged in latest to older minute.
           ";
       }
       leaf state {
          type maps-types:credit-stall-state-type;
          description
           "
           Specifies port congestion credit-stall state of sample for given
           minute. State can be one of the following based on the congestion 
           experienced by port:
                frame-loss
                perf-impact
                medium
                low
                info
                no-congestion
		monitoring-paused
           ";
       }
       leaf frequency {
          type uint8 {
           range "0..60";
          }
          description
           "
           Specifies number of times port is in congestion state for given
	   minute.
           ";
       }
    }

    list oversubscription-dashboard {
      config false;
      description
        "
        The dashboard congestion provides information about the
        monitored ports.
        ";

       leaf slot-port {
         type fibrechannel:slot-port-name-type;
         description
           "
	   Specifies slot and port information in slot/port format.
           ";
       }
       leaf timestamp {
         type yang:date-and-time;
         description
           "
	   Specifies system time of credit-stall congestion data sample.
	   The congestion data sample is available per minute and it is
	   arranged in latest to older minute.
           ";
       }
       leaf state {
          type maps-types:oversubscription-state-type;
          description
           "
           Specifies port oversubscription state of sample for given minute.
           State can be one of the following based on the oversubscription
           experienced by port:
                oversubscription
                no-oversubscription
		monitoring-paused
           ";
       }
    }

    list rule {
      key "name";
      description
        "
        A list of rules. You can use the rules container to configure and 
        manage MAPS monitoring rules and to display configured rules. A rule 
        associates a condition (threshold) with actions that are triggered when 
        the specified condition is reached. A rule must be in the enabled MAPS 
        policy to be active. When you modify a rule in the enabled MAPS policy,
        the rule does not take effect until you re-enable the policy.
        ";
 
      leaf name {
        type maps-types:maps-rule-name-type;
        description
          "
          The rule name.
          ";
      }
      leaf is-rule-on-rule {
        type maps-types:maps-rule-type;
        mandatory true;
        description
          "
          The rule name. A rule can be one of two types: base or rule-on-rule. 
          A base rule monitors the statistics or FRUs whereas a rule-on-rule 
          monitors the base rule.
          ";
      }
      leaf monitoring-system {
        type maps-types:maps-monitoring-system-type;
        mandatory true;
        description
          "
          The statistic or error to be monitored (CRC, ITW, PS_STATE, 
          and so on).
          ";
      }
      leaf time-base {
        type maps-types:maps-time-base-type;
        mandatory true;
        description
          "
          The time interval between two samples to be compared.
          ";
      }
      leaf logical-operator {
        type maps-types:maps-logical-operator-type;
        mandatory true;
        description
          "
          The relational operation to be used in evaluating the condition.
          ";
      }
      leaf threshold-value {
        type maps-types:threshold-value-type;
        mandatory true;
        description
          "
          The threshold value. Thresholds are the values at which potential 
          problems might occur. For example, in configuring a port threshold, 
          you can select a specific value at which an action is triggered 
          because of too many threshold violations.
          ";
      }
      leaf group-name {
        type maps-types:maps-group-name-type;
        must "(../is-rule-on-rule = false and ../group-name != '') or "+
             "(../is-rule-on-rule = true and "+
              "(../group-name = '' or ../group-name = 'RULE'))";
        description
          "
          The group name (such as ALL_PORTS).
          ";
      }
      container actions {
        description
          "
          The MAPS actions.
          ";
          leaf-list action {
            type maps-types:maps-generic-action-type;
            min-elements 1;
            description
              "
              A MAPS action.
              ";
          }
      }
      leaf is-predefined {
        type boolean;
        config false;
        description
          "
          Whether the group is a system-defined or user-defined group. 
          You cannot delete system-defined groups; however, you can augment the 
          ports managed by the group.
          true : The group is system-defined. 
          false: The group is user-defined.
          ";
      }
      leaf event-severity {
        type maps-types:maps-event-severity-type;
        description
          "
          The user configured severity. 
          For default rules severity is NULL. For more information for the
          default severity please refer the MAPS admin guide.
          ";
      }
      leaf toggle-time {
        when "../actions/action == port-toggle";
        type uint32 {
          range "2..3600";
        }
        units "second";
        description
          "
          The port's toggle time.
          ";
      }
      leaf quiet-time {
	when "../monitoring-system-matrix/monitoring-system != IT_FLOW";
        type uint32 {
          range "0|60..2592000";
        }
        units "second";
	default 0;
        description
          "
          The quiet time. The rule is not triggered until quiet time 
          has expired.
          This leaf node is not suuported for IT_FLOW monitoring system.
          ";
      }
      leaf quiet-time-clear {
        type boolean;
        default false;
        status deprecated;
        description
          "
          Whether to clear quiet time.
          true : Clears the quiet time from the rule. 
          false: Does not clear the quiet time from the rule.
          quiet-time leaf with 0 value can be used to clear the quiet time. 
          NOTE: write-only leaf node and would not be present in GET request.
          ";
      }
      leaf un-quarantine-timeout {
        when "../actions/action == un-quarantine";
        type uint32 {
          range "0..2147483647";
        }
        units "second";
        description
          "
          The un-quarantine timeout.
          ";
      }
      leaf un-quarantine-clear {
        type boolean;
        description
          "
          Whether to clear the un-quarantine timeout.
          true : Clears the quiet time from the rule. 
          false: Does not clear the quiet time from the rule.
          NOTE: write-only leaf node and would not be present in GET request.
          ";
        }
      }
      list maps-policy {
        key "name";
        description
          "
          The MAPS policy. This container enables you to create and manage 
          monitoring policies. A MAPS policy is a set of rules that define 
          thresholds for measures and actions to take when a threshold 
          is triggered. When you enable a policy, all of the rules in the 
          policy are in effect. A switch can have multiple policies.
          ";

        leaf name {
          type maps-types:maps-policy-name-type;
          description 
            "
            The MAPS policy name.
            ";
        }
        container rule-list {
          description
            "
            A list of rules in the policy.
            ";
          leaf-list rule {
            type maps-types:maps-rule-name-type;
            description
              "
              The rule name.
              ";
          }
        }
        leaf is-active-policy {
          type boolean; 
          default false;
          description
            "
            Whether the policy is active. You can configure multiple policies; 
            however, only one policy can be active at a time.
            true : This policy is active. 
            false: This policy is not active.
            ";
        }
        leaf is-predefined-policy {
          type boolean; 
          config false;
          description
            "
            Whether the policy is predefined or user-defined. Fabric OS ships 
            with 4 predefined policies (dflt_conservative_policy, 
            dflt_aggressive_policy, dflt_moderate_policy, and dflt_base_policy).
            true : This policy is predefined. 
            false: This policy is user-defined.
            ";
        }
    }

    list monitoring-system-matrix {
      key "monitoring-system group-type";
      config false;
      description
        "
        A list of monitoring systems. Each monitoring system can support
        different time bases, actions, and thresholds. Some monitoring systems 
        are supported only on specific systems. For example, circuit or tunnel
        monitoring systems are only supported on extension platforms.
        ";
      leaf monitoring-system {
        type maps-types:maps-monitoring-system-type;
        description
          "
          The monitoring system name. 
          ";
      }
      leaf group-type {
        type maps-types:maps-group-type-type;
        description
          "
          The group type.
          ";
      }
      leaf dashboard-category {
        type maps-types:maps-dashboard-category-type;
        description
          "
          The dashboard category of the monitoring system.
          ";
      }
      container base-time-bases {
        description
          "
          The time bases.
          ";
        leaf-list time-base {
          type maps-types:maps-time-base-type;
          description
            "
            A list of the supported time bases for the monitoring system.
            ";
        }
      }
      container rule-on-rule-time-bases {
        when "../is-rule-on-rule-supported = true";
        description
          "
          The supported rule on rules time bases for the monitoring system.
          ";
        leaf-list rule-on-rule-time-base {
          type maps-types:maps-time-base-type;
          description 
            "
            A list of the supported time bases for rule on rules for the 
            monitoring system.
            ";
        }
      }
      leaf is-read-only {
        type boolean;
        description 
          "
          Whether the monitoring system is read only.
          ";
      }
      leaf monitored-logical-switch {
        type enumeration {
          enum "all-logical-switches" {
            description
              "
              The monitoring system is in all the logical switches.
              "; 
          }
          enum "default-switch-only" {
            description
              "
              The monitoring system is only in the default logical switch.
              "; 
          }
        }
        description 
          "
          Whether the monitoring system is in all logical switches or only 
          the default logical switch.
          ";
      }
      leaf is-rule-on-rule-supported {
        type boolean;
        description
          "
          Whether rule on rule is supported.

          true : Rule on rule is supported.
          false: Rule on rule is not supported.
          ";
      }
      leaf is-quiet-time-supported {
        type boolean;
        description 
          "
          Whether quiet time is supported.
          
          true  : Quiet time is supported
          false : Quiet time is not supported
          ";
      }
      leaf minimum-quiet-time {
        when "../is-quiet-time-supported = true";
        type uint32 {
          range "60..31536000";
        }
        units "second";
        description 
          "
          The minimum quiet time.
          ";
      }
      leaf monitoring-type {
        type maps-types:monitoring-type-type;
        description 
          "
          The monitoring type(event based or poll based) for the 
          monitoring system. 
          ";
      }
      leaf data-type {
        type maps-types:data-type-type;
        description 
          "
          The data type support. Each monitoring system supports different 
          data types for thresholds.
          ";
      }
      leaf description {
        type string {
          length "1..128";
        }
        description 
          "
          A description of the monitoring system.
          ";
      }
      container actions {
        description
          "
          The global MAPS actions list.
          ";
        leaf-list action {
          type maps-types:maps-generic-action-type;
          description
            "
            A list of the MAPS actions defined for this monitoring system. 
            ";
        }
      }
      leaf unit {
        type maps-types:maps-data-unit;
        description
          "
          The data unit.
          ";
      }
      leaf data-range {
        type string {
          length "0..100";
          pattern "[0-9]*[A-Z]*[_,-]";
        }
        description
          "
          The data range.
          ";
      }
      container logical-operators {
        description
          "
          The supported operations.
          ";
        leaf-list logical-operator {
          type maps-types:maps-logical-operator-type;
          description
            "
            The logical operator.
            ";
        }
      }
    }
    list fpi-profile {
        key "name";
        description
          "
          The FPI profile. This container enables you to create and manage 
          Fabric Performance Impact monitoring thresholds. The FPI Profile
		  is a set of FPI states such as performance impact, frame loss
		  and thresholds for each state are Transmit Queue Latency (TXQL),
		  CREDIT-ZERO buffer. The FPI rules in MAPS policy gets the thresholds
		  for each state from the active FPI profile.
		  The FPI profile is per logical switch.
          ";

        leaf name {
          type maps-types:maps-policy-name-type;
          description 
            "
            The FPI profile name.
            ";
        }
        leaf predefined-profile {
          type boolean; 
          config false;
          description
            "
            Whether the profile is predefined or user-defined. Fabric OS ships 
            with 1 predefined profile(dflt_fpi_profile)
            true : This profile is predefined. 
            false: This profile is user-defined.
            ";
        }
        container performance-impact {
          description
            "
            The performance-impact FPI state is due to Transmit Queue Latency
			or Credit-Zero stats violation.
            ";
          leaf transmit-queue-latency {
            type uint32 {
              range "1..50";
            }
            units "milliseconds";
       	    mandatory true;
            description 
            "
            The Transmit Queue latency(TXQL) threshold in milliseconds.
            ";
          }
          leaf credit-zero-percentage-1-sec {
            type uint32 {
              range "50..100";
            }
            units "percentage";
       	    mandatory true;
            description 
            "
            The credit-zero buffer stats threshold percentage in 1-second.
            ";
          }
          leaf credit-zero-percentage-5-sec {
            type uint32 {
              range "30..100";
            }
            units "percentage";
       	    mandatory true;
            description 
            "
            The credit-zero buffer stats threshold percentage in 5-second.
            ";
          }
          leaf credit-zero-percentage-10-sec {
            type uint32 {
              range "10..100";
            }
            units "percentage";
       	    mandatory true;
            description 
            "
            The credit-zero buffer stats threshold percentage in 10-second.
            ";
          }
        }
        container frame-loss {
          description
            "
            The frame loss FPI state is due to frame transmit timeout or
            high Transmit Queue Latency(TXQL) that could possibly lead
            to frame drop condition.
            ";
          leaf transmit-queue-latency {
            type uint32 {
              range "50..200";
            }
            units "milliseconds";
       	    mandatory true;
            description 
            "
            The Transmit Queue Latency(TXQL) threshold in milliseconds.
            ";
          }
		}
        container port-oversubscription {
          config false;
          description
            "
            The port-oversubscription FPI state is due to high Transmit Queue
            Latency than regular traffic condition and more than 98% TX
            utilization.
            ";
          leaf transmit-percentage {
            type uint32 {
              range "98..100";
            }
            units "percentage";
            description 
            "
            The Transmit(TX) utilization in percentage.
            ";
          }
		}
    }

  grouping dashboard-port-data {
    description
      "
       A list of the port objects.
      ";

    leaf-list port-data {
      type string {
        length "0..128";
      }

      description
        "
         A list of the port objects along with violation counters in
         'slot/port:counter' format. The counters do not roll over to next
         date. At midnight, these counters are moved to next
         historical date and the current date counters start again
         from zero.
        ";
    }
  }

    list dashboard-history {
      config false;
      description
        "
        The historical data of various counters.
        ";

      leaf category {
        type string {
          length "0..20";
          pattern 'fc-port';
        }
        description
          "
          Logical grouping of the counters.
          ";
      }
      leaf date {
        type string {
         pattern 'current|[0-9]{2}\-[0-9]{2}\-[0-9]{2}';
        }
        description
          "
          Date of the day when the counters' data was cached
          ";
      }
      container crc-errors {
        description
          "
          The group of ports on which the CRC (Cyclic Redundancy Check) errors
          were detected. The list of ports is sorted based on number of errors
          detected on the ports.
          ";
        uses dashboard-port-data;
      }
      container itw-errors {
        description
          "
          The group of ports on which the ITW (Invalid Transmit Words) errors
          were detected. The list of ports is sorted based on number of errors
          detected on the ports.
          ";
        uses dashboard-port-data;
      }
      container link-failure {
        description
          "
          The group of ports on which the Link Failure errors were detected.
          The list of ports is sorted based on number of errors detected on
          the ports.
          ";
        uses dashboard-port-data;
      }
      container signal-loss {
        description
          "
          The group of ports on which the Signal Loss errors were detected.
          The list of ports is sorted based on number of errors detected on
          the ports.
          ";
        uses dashboard-port-data;
      }
      container protocol-errors {
        description
          "
          The group of ports on which the  Protocol Errors were detected.
          The list of ports is sorted based on number of errors detected on
          the ports.
          ";
        uses dashboard-port-data;
      }
      container state-change {
        description
          "
          The group of ports on which state changes were detected. The list
          of ports is sorted based on number of state changes detected on the
          ports.
          ";
        uses dashboard-port-data;
      }
      container link-reset {
        description
          "
          The group of ports on which the Link Resets were detected. The list
          of ports is sorted based on number of link resets detected on the
          ports.
          ";
        uses dashboard-port-data;
      }
      container c3-tx-to {
        description
          "
          The group of ports on which the Class-3 frame Time-outs were
          detected. The list of ports is sorted based on number of frames
          timeed-out on the ports.
          ";
        uses dashboard-port-data;
      }
      container rx-perf {
        description
          "
          The list of ports sorted based on percentage of RX bandwidth used
          on the port.
          ";
        uses dashboard-port-data;
      }
      container tx-perf {
        description
          "
          The list of ports sorted based on percentage of TX bandwidth used
          on the port.
          ";
        uses dashboard-port-data;
     }
     container utilization {
        description
          "
          The list of ports sorted based on percentage of total bandwidth
          (RX + TX) used on the port.
          ";
        uses dashboard-port-data;
    }
  }

  }
}
