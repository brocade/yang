module brocade-name-server {

  yang-version 1.1;
  namespace "urn:brocade.com:mgmt:brocade-name-server";
  prefix brocade-name-server;

  import fibrechannel-yang-types {
    prefix fibrechannel;
  }

  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    This module is used to manage the Fibre Channel (FC) Name Server,
    which realizes the FC-GS-6 requirements.

    This module provides monitoring the operation of, and configuring 
    some parameters of, one or more instances of Fibre Channel Name 
    Server functionality.

    The Fibre Channel Name Server provides a way for N_Ports and
    NL_Ports to register and discover Fibre Channel attributes.
    Such attributes include names, addresses, types, features,
    and so on, at various protocol layers, including upper layer
    protocols specific to Fibre Channel (sometimes called FC-4s). 

    Physically, Fibre Channel is an interconnection of multiple
    communication points, called N_Ports, interconnected either by
    a switching network, called a Fabric, or by a point-to-point
    link. A Fibre Channel 'node' consists of one or more N_Ports.
    A Fabric may consist of multiple Interconnect Elements, some
    of which are switches.  An N_Port connects to the Fabric via a
    port on a switch called an F_Port.  When multiple FC nodes are
    connected to a single port on a switch via an 'Arbitrated Loop'
    topology, the switch port is called an FL_Port, and the nodes'
    ports are called NL_Ports.  The term Nx_Port is used to refer
    to either an N_Port or an NL_Port.

    Copyright © 2019 Broadcom. All rights reserved. The term 'Broadcom' refers
    to Broadcom Inc. and/or its subsidiaries.
    ";

  reference
    "
    ANSI INCITS 332-1999, Fibre Channel - Arbitrated Loop - 2 (FC-AL-2).

    ANSI INCITS 433-2006, Fibre Channel - Link Services (FC-LS).

    ANSI INCITS 463-2010, Fibre Channel - Generic Services - 6 (FC-GS-6).

    ANSI INCITS 545-20xx Rev 0.2, Fibre Channel - Framing and Signaling - 5
    (FC-FS-5).
    ";

  revision 2020-02-06 {
    description
      "
      FOS 8.2.0a
      -----
        Initial release

      FOS 8.2.1
      -----
        Refine descriptions
        Refine 'link-speed' regular expression
        Formatting
        Organization information

      FOS 9.0.0
      -----
        Update 'lsan' type
        Add 'fibrechannel_switch_platform' feature check
        Update patterns for correctness
        Update leaf 'share-area' status obsolete
      ";
    reference
      "None";
  }

  container brocade-name-server {
    config false;
    description
      "
      Proprietary Name Server directory entry container.
      ";

    list fibrechannel-name-server {
      if-feature fibrechannel:fibrechannel_switch_platform;
      key "port-id";
      description
        "
        The Port Identifier serves as the unique data base key for the
        Name Server.
        ";

      leaf port-id {
        type fibrechannel:fcid-hex-string-type;
        description
          "
          A Fibre Channel address identifier assigned to an Nx_Port during
          either implicit or explicit fabric logins. The format of the port 
          identifier is identical to the address identifier format. The 
          port identifier serves as the unique data base key for the Name
          Server.
          ";
      }

      leaf port-name {
        type fibrechannel:wwn-type;
        description
          "
          The device port world wide name (WWN).
          ";
      }

      leaf port-symbolic-name {
        type string {
          length "0..384";
          pattern "[ -~]*";
        }
        description
          "
          The symbolic port name registered with the Name Server. It is
          subject to all the description and constraints of that object.

          The registered value displays within double quotes and is preceded
          by a numeric value indicating the length of the registered data. The
          numeric value is encapsulated within brackets.
          For example: [30] \"dsim:brcdtgt:sw0[10.10.10.100]\"
          ";
      }

      leaf fabric-port-name {
        type fibrechannel:wwn-type;
        description
          "
          The F_Port WWN to which the N_Port connects.
          ";
      }

      leaf permanent-port-name {
        type fibrechannel:wwn-type;
        description
          "
          The Name_Identifier associated with the physical Nx_Port. If there
          are  multiple Name_Identifiers associated with a single physical 
          Nx_Port via FDISC (see FC-FS) the permanent port name is the
          original Name_Identifier associated with that physical Nx_Port at
          fabric login.
          ";
      }

      leaf node-name {
        type fibrechannel:wwn-type;
        description
          "The device port world wide name (WWN).";
      }

      leaf node-symbolic-name {
        type string {
          length "0..384";
          pattern "[ -~]*";
        }
        description
          "
          The name registered with the Name Server as a Name Server symbolic 
          node name object and is subject to all the description and 
          constraints of that object. If not all Nx_Ports on the host bus 
          adapter have the same node name, the node-symbolic-name resource 
          is not returned for the host bus adapter.

          The registered value displays within double quotes and is preceded
          by a numeric value indicating the length of the registered data. The
          numeric value is encapsulated within brackets.
          For example: [30] \"dsim:brcdtgt:sw0[10.10.10.100]\"
          ";
      }

      leaf class-of-service {
        type fibrechannel:class-of-service-type;
        description
          "
          The Class of Service (CoS) levels supported by the device. A device
          can support multiple CoS levels.
          ";
      }

      leaf fc4-type {
        type fibrechannel:fc4-type-type;
        description
          "
          A set of supported data structure type values (for example,
          supported values of the type field in frame headers) for 
          Device_Data and FC-4 Link_Data frames. 
          ";
      }

      leaf fc4-features {
        type fibrechannel:fc4-features-type;
        description
          "
          The registered FC-4 features bits for a given FC-4 type.
          ";
      }

      leaf port-type {
        type fibrechannel:port-type-string-type;
        description
          "
          The port type of the device.
          ";
      }

      leaf state-change-registration {
        type string {
          length "0..256";
          pattern "( |None|Fabric-Detected|Nx-Port-Detected|Fabric-Name|" +
                  "Peer-Zone|Brocade-Principal-Switch|Brocade-QoS)*";
        }
        description
          "
          The state change registration (SCR) of the device. Returns an empty
          tag if the SCR value is not known.

          None:
            No registration. The device has not registered for any Remote 
            State Change Notifications (RSCN) function.

          Fabric-Detected:
            Registered to receive all RSCN for events detected by the fabric.

          Nx-Port-Detected:
            Registered to receive all RSCN requests issued for events detected 
            by the affected Nx_Port.

          Fabric-Name:
            Fabric Name change registration (FC Standard variant). Registered 
            to receive an RSCN when the Fabric Principal switch changes.

          Peer-Zone:
            Registered to receive an RSCN when an associated Peer Zone changes.

          Brocade-Principal-Switch:
            Principal switch change registration (proprietary).

          Brocade-QoS:
            Access Gateway Quality-of-Service change registration (proprietary).
          ";
      }

      leaf name-server-device-type {
        type string {
          length "0..64";
          pattern '(Undefined|Physical|Virtual|NPIV|iSCSI|FCoE) ' +
                  '(Undefined|Unknown\(initiator/target\)|Initiator|' +
                  'Target|Initiator\+Target)';
        }
        description
          "
          The definition for the type and role of a device. The device type
          can be Physical, Virtual, NPIV, or iSCSI. If the device type is not 
          Physical, Virtual, NPIV, or iSCSI, the type displays as 'Undefined'. 
          The role can be Initiator, Target, or Initiator+Target. If the device 
          role is not registered, the role displays as 'Unknown'.
          ";
      }

      leaf port-index {
        type fibrechannel:user-port-number-type;
        description
          "
          The index number of the physical N_Port to which the device connects.
          ";
      }

      leaf share-area {
        type string {
          length "0..4";
          pattern "yes|no";
        }
        status obsolete;
        description
          "
          Indicates whether or not the port utilizes the Brocade Shared Area
          method of Fibre Channel addressing.

          yes   : The port shares an area.
          no    : The port does not share an area.
          ";
      }

      leaf frame-redirection {
        type string {
          length "0..4";
          pattern "yes|no";
        }
        description
          "
          Indicates whether or not the port is involved in Frame Redirection 
          zoning. The device involved in frame redirection is specified as 
          either 'virtual', 'host', or 'target'.

          yes   : The port is involved in frame redirection.
          no    : The port is not involved in frame redirection.
          ";
      }

      leaf partial {
        type string {
          length "0..4";
          pattern "yes|no";
        }
        description
          "
          Indicates whether or not the device entry is incomplete. Incomplete 
          devices have routing established, but are not considered during
          device discovery (for example, during FC-GS Name Server queries).

          yes   : The device entry is incomplete.
          no    : The device entry is complete.
          ";
      }

      leaf lsan {
        type enumeration {
          enum "yes" {
            description "The device is a member of an active LSAN zone.";
          }
          enum "no" {
            description "The device is not a member of an active LSAN zone.";
          }
          enum "unknown" {
            description "The LSAN zone status is not known.";
          }
        }
        description
          "
          Indicates whether or not the device is part of an active LSAN zone.
          ";
      }

      leaf link-speed {
        type string {
          length "0..8";
          pattern "(([1-8]|([1-8][0-9]{0,1}[0-9]{0,1}[0-9]{0,1}))G)?";
        }
        description
          "
          The link speed of the device (for example, 4G, 8G, 16G, and so on.) 
          The link speed of end devices that log in to the edge fabric through 
          F_Port trunk display the bandwidth of the F_Port trunk. For example, 
          if an 8G host attached to AG login to the fabric through a 32G
          F_Port trunk, the device link speed for the 8G host is displayed 
          as 32G.
          ";
      }

      leaf port-properties {
        type string {
          length "0..64";
          pattern "( |SIM Port|Mirror Port|I/O Analytics Port)*";
        }
        description
          "
          A list of proprietary port properties (for example, 'SIM Port'
          for Brocade SIM ports).
          ";
      }

      leaf cascaded-ag {
        type string {
          length "0..4";
          pattern "yes|no";
        }
        description
          "
          Indicates whether or not the device is connected via a cascaded Access
          Gateway (AG) connection.

          yes   : The device is connected through a cascaded AG connection (for 
		  example, a 2-hop AG connection).
          no    : The device is not connected through a cascaded AG connection.
          ";
      }

      leaf connected-through-ag {
        type string {
          length "0..4";
          pattern "yes|no";
        }
        description
          "
          Indicates whether or not the device is connected through AG.

          yes   : The device is connected through AG.
          no    : The device is not connected through AG.
          ";
      }

      leaf real-device-behind-ag {
        type string {
          length "0..4";
          pattern "yes|no";
        }
        description
          "
          Indicates whether or not the device is a virtualized device (NPIV)
          connected through AG.

          yes   : The device is not a virtualized device (NPIV) connected
                  through AG.
          no    : The device is a virtualized device (NPIV) connected 
                  through AG.
          ";
      }

      leaf fcoe-device {
        type string {
          length "0..4";
          pattern "yes|no";
        }
        description
          "
          Indicates whether or not the device is an FCoE device.

          yes   : The device is an FCoE device.
          no    : The device is not an FCoE device.
          ";
      }

      leaf slow-drain-device-quarantine {
        type string {
          length "0..4";
          pattern "yes|no";
        }
        description
          "
          Indicates whether or not the device has been identified as having
          symptoms of credit stalling.

          yes   : The device has been identified as having a credit stalled
                  condition, and has its incoming traffic quarantined to a
                  Low Priority VC.
          no    : The device has not been flagged for having a credit stalled
                  issue.
          ";
      }
    }
  }
}
