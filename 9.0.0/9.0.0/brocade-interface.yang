module brocade-interface {

  yang-version 1.1;
  namespace "urn:brocade.com:mgmt:brocade-interface";
  prefix brocade-interface;

  import ietf-inet-types {
    prefix inet;
  }
  import fibrechannel-yang-types {
    prefix fibrechannel;
  }
  import ietf-yang-types {
    prefix yang;
  }
  import brocade-interface-types {
    prefix brocade-interface-types;
  }
  import ietf-yang-types {
    prefix ietf;
  }
  import brocade-extension-types {
    prefix extension;
  }

  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    This module contains a collection of YANG definitions for managing
    brocade-interfaces.
     
    Copyright © 2019 Broadcom. All rights reserved. The term 'Broadcom' refers
    to Broadcom Inc. and/or its subsidiaries.
    ";

  revision 2020-02-18 {
    description
      "
      Fabric OS 8.2.1b
      ---------------
        Reorganization of 8.2.0 yang
        Refine descriptions
      -----------------------------
      brocade-extension-ip-interface.yang
      brocade-gigabitethernet.yang
      Organization information

      Fabric OS 9.0.0
      ---------------
        Added logical-e-port list
        Added portchannel list
      ";
    reference
      "None";
  }

  typedef portchannel-type {
    type enumeration {
      enum "static" {
        description
          "
          The static portchannel type.
          ";
      }
      enum "dynamic" {
        description
          "
          The dynamic portchannel type.
          ";
      }
    }
    description
      "
      The portchannel can be of either static or dynamic type
     ";
  }

  typedef lag-port-timeout {
    type enumeration {
      enum "short" {
        description
          "
          The short member port timeout
          timeout value is 3 sec
          ";
      }
      enum "long" {
        description
          "
          The long member port timeout
          timeout value is 90 sec
          ";
      }
    }
    description
      "
      The portchannel member can have short or long timeout configured.
     ";
  }

  typedef port-type-string-type {
    type enumeration {
      enum "e-port" {
        description
          "
	  Port is an E-port.
          ";
      }
      enum "g-port" {
        description
          "
	  Port is a G-port.
          ";
      }
      enum "universal-port" {
        description
          "
	  If port is not configured for any type.
          ";
      }
      enum "f-port" {
        description
          "
	  Port is a F-port.
          ";
      }
      enum "l-port" {
        description
          "
	  Port is a Logical port.
          ";
      }
      enum "fcoe-port" {
        description
          "
	  Port is a FCoE-port.
          ";
      }
      enum "ex-port" {
        description
          "
	  Port is a EX-port.
          ";
      }
      enum "d-port" {
        description
          "
	  Port is Diagnostic port.
          ";
      }
      enum "sim-port" {
        description
          "
	  Port is SIM-port.
          ";
      }
      enum "af-port" {
        description
          "
	  Port is AF-port. Present only on AMP switches.
          ";
      }
      enum "ae-port" {
        description
          "
	  Port is an AE-port.
          ";
      }
      enum "ve-port" {
        description
          "
	  Port is a VE-port.
          ";
      }
      enum "ethernet-port" {
        description
          "
	  Port is a Ethernet Flex port.
          ";
      }
      enum "flex-port" {
        description
          "
	  Port is a Flex-port.
          ";
      }
      enum "n-port" {
        description
          "
	  Port is N-port. Applicable for AG mode.
          ";
      }
      enum "mirror-port" {
        description
          "
	  Port is Mirror-port.
          ";
      }
      enum "encryption-support-port" {
        description
          "
	  Port is an Encryption Support Port. A front end port
	  reserved for Encryption block to work.
          ";
      }
      enum "loopback-port" {
        description
          "
	  Port is a Loopback port.
          ";
      }
      enum "unknown-port" {
        description
          "
	  If Port is online and does not belong any known port type.
          ";
      }
    }
    description
      "
      Supported Fibre Channel port types:
      ";
  }
  typedef port-type-type {
    type uint16 {
      range "0|7|10|11|15|16|17|19|20|21|22|23|25|26|32768";
    }
    status deprecated;
    description
      "
      Fibre Channel port types:

      0     : Unknown
      7     : E Port
      10    : G Port
      11    : U Port
      15    : F Port
      16    : L Port
      17    : FCoE Port
      19    : EX Port
      20    : D Port
      21    : SIM Port
      22    : AF Port
      23    : AE Port
      25    : VE Port
      26    : Ethernet Flex Port
      29    : Flex Port
      30    : N Port
      31    : Mirror Port
      32768 : LB Port
      Deprecated. Please use port-type-string-type in stead.
      ";
  }

  typedef speed-type {
    type uint64 {
      range "0|1000000000|2000000000|4000000000|8000000000|10000000000|" +
            "16000000000|32000000000|64000000000";
    }
    description
      "
      The current bandwidth of the port.

      0             : Auto negotiated.
      1000000000    : 1 GFC
      2000000000    : 2 GFC
      4000000000    : 4 GFC
      8000000000    : 8 GFC
      10000000000   : 10 GFC
      16000000000   : 16 GFC
      32000000000   : 32 GFC
      64000000000   : 64 GFC
      ";
  }

  container brocade-interface {
    description
      "Represents the Brocade interfaces on a blade or system.";
    list fibrechannel {
      key "name";
      description
        "
        A list of interfaces on the device.

        System-controlled interfaces created by the system are
        always present in this list, whether they are configured or not.
        ";
      leaf name {
        type string {
          /* pattern with 12 slots and 1024 ports separated by a slash */
          pattern "([1-9]|1[0-9])/(10[0-2][0-9]|[1-9][1-9][0-9]|[1-9][1-9]|" + 
                  "[1-9])";
        }
        description
          "
          The name of the interface. The slot and port number of the specified 
          port in the format slot/port.
          ";
      }
      leaf wwn {
        type fibrechannel:wwn-type;
        config false;
        description
          "
          The world wide name (WWN) of the specified port.
          ";
      }
      leaf operational-status {
        type uint32 {
          range "0|2|3|5|6";
        }
        config false;
        description
          "
          The current operational status of the specified port. The possible 
          values are:

          0 : Undefined
          2 : Online
          3 : Offline
          5 : Faulty
          6 : Testing 
          ";
      }
      leaf enabled-state {
        type uint32 {
          range "2|6";
        }
        status deprecated;
        description
          "
          The current state of the specified port. The possible values are:

          2 : Enabled.
          6 : Disabled.
          Deprecated: Please use 'is-enabled-state' leaf instead.
          ";
      }
      leaf is-enabled-state {
        type boolean;
        description
          "
          The current state of the specified port. The possible values are:

          true  : Enabled.
          false : Disabled.
          ";
      }
      leaf user-friendly-name {
        type string {
          length "0..128";
          pattern "[ -~]*";
          pattern '[\(\),;@]+' {
            modifier invert-match;
          }
        }
        description
          "
          A user-friendly name to be assigned to the specified port.

          A value from 1 to 128 alphanumeric characters. This name must not 
          contain special (high-ASCII) characters, and is not case-sensitive.

          When a port name is not configured, a default name is assigned.
          The format of the default name is as follows:

            - On standalone platforms, the default port name displays as
              port<port_number>, for example, port10.
            - On enterprise-class platforms, the default port name displays as
              slot<slot_number> port<port_number>, for example, slot1 port5.

          Provide a null string to replace the existing name with the default.
          ";
      }
      leaf speed {
        type brocade-interface-types:fc-speed-type;
        description
          "
          The Fibre Channel interface may operate at various speeds; this leaf 
          allows the port interface to be forced to operate at a particular 
          speed. 
          
          Without any explicit speed set (for example, having the 
          auto-negotiate value set), the Fibre Channel interfaces run at the 
          maximum speed, subject to speed negotiations with their neighbor. 
          
          The value zero is returned only when auto-negotiate is set and the 
          port has not yet negotiated the speed with the other end (for example,
          if the port is offline or is syncing). Otherwise, the negotiated 
          speed or the fixed speed is returned. 
          
          To determine whether the speed was auto-negotiated or fixed,
          see the auto-negotiate leaf.
          ";
      }
      leaf max-speed {
        type brocade-interface-types:fc-speed-type;
        config false;
        description
          "
          The maximum speed the port is capable of supporting, in bits 
          per second.
          ";
      }
      leaf auto-negotiate {
        type uint8 {
          range "0..1";
        }
        config false;
        description
          "
          Whether the port speed is auto-negotiated on the specified port.

          0 : Port speed is fixed.
          1 : Port speed is auto-negotiated.
          ";
      }
      leaf g-port-locked {
        if-feature fibrechannel:fibrechannel_switch_platform;
        type uint8 {
          range "0..1";
        }
        status obsolete;
        description
          "
          Designates the specified port as a G_Port. After successful execution,
          the switch attempts to initialize the specified port as an F_Port 
          only and does not attempt loop initialization (FL_Port) on the port. 
          A port that is designated as a G_Port can become an E_Port. This 
          configuration can be cleared but not set on VE or VEX_Ports. Changes 
          made by this command are persistent across switch reboots or 
          power cycles.

          0 : Unlocked (removes the G_Port designation from the port).
          1 : Locked (the port is designated as a G_Port).
          ";
      }
      leaf e-port-disable {
        if-feature fibrechannel:fibrechannel_switch_platform;
        type uint8 {
          range "0..1";
        }
        description
          "
          Enables or disables E_Port capability on the specified port or locks 
          down the specified port as an E_Port. E_Port capability is enabled by 
          default. When an inter-switch link (ISL) is connected to a port and 
          the E_Port capability of the port is disabled, the ISL is segmented, 
          and all traffic between the switches stops. Fabric management data, 
          such as zoning information, can no longer be exchanged through 
          this port.

          0 : Enables the port as an E_Port. This is the default port state.
          1 : Disables E_Port capability for the specified port.
          ";
      }
      leaf n-port-enabled {
        if-feature fibrechannel:access_gateway_platform;
        type uint8 {
          range "0..1";
        }
        description
          "
          Indicates whether this port can operate as an N_Port. A port can 
          operate as an N_Port only in Access Gateway Mode.

          0 : N_Port is disabled as an N_Port.
          1 : N-Port is enabled as an N_Port.
          ";
      }
      leaf d-port-enable {
        type uint8 {
          range "0..1";
        }
        description
          "
          Indicates whether this port is configured as a D_Port.

          0 : Port is disabled as a D_Port.
          1 : Port is enabled as a D_Port.
          ";
      }
      leaf persistent-disable {
        type uint8 {
          range "0..1";
        }
        description
          "
          Status of the persistent-disable feature of the port.

          0 : Persistent-disable is not active for the port.
          1 : Persistent-disable is active for the port.
          ";
      }
      container neighbor {
        config false;
        description
          "
          A list of WWN's.
          ";
        leaf-list wwn {
          type fibrechannel:wwn-type;
          description
            "
            The Fibre Channel WWN of the neighbor port.
            ";
        }
      }
      leaf neighbor-node-wwn {
        when "operational-status = 2";
        type fibrechannel:wwn-type;
        config false;
        description
          "
          The  neighbor node WWN connected to this port.
          ";
        }
      leaf fcid {
        type fibrechannel:fcid-type;
        config false;
        status deprecated;
        description
          "
          The Fibre Channel ID (FCID) of the port (decimal format).

          Deprecated: Please use 'fcid-hex' leaf instead.
          ";
      }
      leaf fcid-hex {
        type fibrechannel:fcid-hex-string-type;
        config false;
        description
          "The Fibre Channel ID (FCID) of the port (hexadecimal format).";
      }
      leaf port-type {
        type brocade-interface-types:port-type-type;
        config false;
        status deprecated;
        description
          "
          The port type currently enabled for the specified port. If this port 
          is logged in, this will be the negotiated port type; otherwise, the 
          configured port type will be reported.
          Deprecated: Please use 'port-type-string' leaf instead.
          ";
      }
      leaf port-type-string {
        type port-type-string-type;
        config false;
        description
          "
          This attribute represents currently enabled port-type for the
          specified port. If this port is logged in, this will be the
          negotiated port type; otherwise, the configured port type will
          be displayed.
          ";
      }

      leaf qos-enabled {
        type uint8 {
          range "0..1";
        }
        description
          "
          Indicates whether QoS is enabled on the port.

          0 : Port QoS disabled.
          1 : Port QoS enabled.
          ";
      }
      leaf compression-configured {
        if-feature fibrechannel:fibrechannel_switch_platform;
        type uint8 {
          range "0..1";
        }
        description
          "
          Enables or disables the compression configuration on the specified 
          port. This change is persistent. Configuring a port for compression 
          is disruptive. You must disable the port before you can enable 
          compression on the port. This command fails on an enabled port. 
          The values are:

          0 : Disables the compression configuration on the specified port.
          1 : Enables the compression configuration on the specified port.
          ";   
      }
      leaf encryption-enabled {
        if-feature fibrechannel:fibrechannel_switch_platform;
        type uint8 {
          range "0..1";
        }
        description
          "Enables or disables the encryption configuration on the port, 
           and saves the change in configuration persistently.
           Configuring a port for encryption is disruptive. 
           You must disable the port before you can enable compression on
           the port. This command fails on an enabled port. The values are:
           
             0 - Disables the encryption configuration on the specified port.
             1 - Enables the encryption configuration on the specified port.

          The number of configurable ports is limited by the platform ASIC.
          ";
      }
      leaf compression-active {
        if-feature fibrechannel:fibrechannel_switch_platform;
        type uint8 {
          range "0..1";
        }
        config false;
        description
          "
          The runtime compression status for the port.

          0 : The port is enabled for compression but offline 
              or is not enabled for compression.
          1 : The port is online and enabled for compression.
          ";
      }
      leaf encryption-active {
        if-feature fibrechannel:fibrechannel_switch_platform;
        type uint8 {
          range "0..1";
        }
        config false;
        description
          "
          The encryption status for the specified port.

          0 : Encryption is disabled.
          1 : Encryption is enabled.
          ";
      }
      leaf target-driven-zoning-enable {
        type uint8 {
          range "0..1";
        }
        description
          "
          Enables or disables the Target Driven Zoning (TDZ) configuration on 
          the port. This change is persistent. TDZ can be configured on online
          or offline E Ports, F Ports, and L Ports; it does not toggle the 
          port to apply the configuration. After TDZ is configured on a port, 
          it allows the connected target device to configure Target Driven Peer
          Zones to be enabled and committed.

          0 : Target Driven Zoning configuration is disabled.
          1 : Target Driven Zoning configuration is enabled.
          ";
      }
      leaf sim-port-enabled {
        if-feature fibrechannel:fibrechannel_switch_platform;
        type uint8 {
          range "0..1";
        }
        description
          "
          Enables or disables the port as a SIM port.

          0 : SIM Port is disabled.
          1 : SIM Port is enabled.
          ";
      }
      leaf mirror-port-enabled {
        type int8 {
          range "0..1";
        }
        description
          "
          Enables or disables the port as a mirror port. Port mirroring 
          reroutes data frames between two devices to the mirror port..

           0 : Mirror Port is disabled.
           1 : Mirror Port is enabled.
          ";
      }
      leaf credit-recovery-enabled {
        type int8 {
          range "0..1";
        }
        description
          "
          Enables or disables credit recovery on the port. Credit recovery 
          enables credits or frames to be recovered.
          
          Configure credit recovery on a port. The credit recovery feature
          enables credits or frames to be recovered. The default credit recovery
          configuration is enabled.

           0 : Credit Recovery is disabled.
           1 : Credit Recovery is enabled.
          ";
      }
      leaf credit-recovery-active {
        type int8 {
          range "0..1";
        }
        config false;
        description
          "
          Whether credit recover is active on the port. Fabric OS must support 
          credit recovery at either end of the link for credit recovery to be 
          active.

           0 : Credit Recovery is not active on the port.
           1 : Credit Recovery is active on the port.
          ";
      }
      leaf fec-active {
        type int8 {
          range "0..1";
        }
        config false;
        description
          "
          Whether forward error correction (FEC) is active on the port. 
          Fabric OS must support FEC at either end of the link for FEC
          to be active.

           0 : FEC is not active on the port
           1 : FEC is active on the port
          ";
      }
      leaf f-port-buffers {
        type uint8 {
          range "0|8..max";
        }
        description
          "
          Configures the buffer allocation for an F_Port. The minimum buffer 
          allocation is the default number of buffers plus 1. The maximum is 
          determined by the remaining buffer allocations in the port's port
          group. If no buffers are configured, the value is zero. 
          
          The F_Port buffer feature is not supported on ports configured as 
          EX_Ports, mirror ports, long distance ports, L_Ports, QoS ports, 
          Fast Write, and trunk areas.
          ";
      }
      leaf e-port-credit {
        type uint8 {
          range "0|5..160";
        }
        description
          "
          Configures the number of credits to be allocated to the specified
          port. The minimum credit allocation is 5, and the maximum can be up
          to 160 depending on the platform.
          0 : E_Port Credit is disabled.
          ";
      }
      leaf csctl-mode-enabled {
        if-feature fibrechannel:fibrechannel_switch_platform;
        type int8 {
          range "0..1";
        }
        description
          "
          Enables or disables Class-Specific Control (CSCTL) mode, which
          enables traffic prioritization based on CS_CTL.

           0 : CSCTL mode is disabled on the port.
           1 : CSCTL mode is enabled on the port.
          ";
      }
      leaf fault-delay-enabled {
        type uint8 {
          range "0..1";
        }
        description
          "
          Configures the fault delay for a port.

          In the event that the link is noisy after a host power cycle, the
          switch may go into a soft fault state, which means a delay of R_A_TOV.
          Setting the mode value to 1 reduces the fault delay value to 1.2
          seconds. The configuration is stored in nonvolatile memory and is
          persistent across switch reboots and power cycles.

          0 : The value is R_A_TOV. This is the default.
          1 : The value is 1.2 seconds.
          ";
      }
      leaf octet-speed-combo {
        type int8 {
          range "1..3";
        }
        description
          "
          The speed configuration for a port octet. Valid Octet Combo
          values include the following:


           1 : Auto-negotiated or fixed port speeds of 32Gbps, 16 Gbps,
               8 Gbps, 4 Gbps, and 2 Gbps

           2 : Auto-negotiated or fixed port speeds of 10 Gbps, 8 Gbps,
               4 Gbps, and 2 Gbps

           3 : Auto-negotiated or fixed port speeds of 16 Gbps and 10 Gbps

          A port octet can be set to any of the three octet combinations, and
          the ports in the octet can run on any speed supported by the port's 
          octet combination. This applies to both auto-negotiated and 
          fixed speeds.

          The octet combination default is 1.
          ";
      }
      leaf long-distance {
        if-feature fibrechannel:fibrechannel_switch_platform;
        type uint8 {
          range "0..7";
        }
        config false;
        description
          "
          The long-distance level. Displays one of the following values
          (the numerical value representing each distance level is shown
          in parentheses):

          0 : Long distance is disabled for this port.
          1 : L0 configures the port as a regular port.
          2 : L1 configures the port as long (<= 50 km).
          3 : L2 configures the port as super long (<= 100km).
          4 : LE configures an E_Port distance as greater than
              5 km and up to 10 km.
          5 : L0.5 configures the port as medium long (<= 25 km).
          6 : LD configures the value as automatic long distance.
          7 : LS mode configures the value as a static long distance link with 
              a fixed buffer allocation greater than 10 km.
          ";
      }
      leaf vc-link-init {
        if-feature fibrechannel:fibrechannel_switch_platform;
        type uint8 {
          range "0..1";
        }
        config false;
        description
          "
          The VC Link initialization.

          0 : The long-distance link initialization option is turned off.
          1 : The long-distance link initialization option is turned on for 
              long-distance mode.
          ";
      }
      leaf isl-ready-mode-enabled {
        if-feature fibrechannel:fibrechannel_switch_platform;
        type uint8 {
          range "0..1";
        }
        description
          "
          Enables or disables ISL ready mode on the port.
          
          0 : ISL R_RDY mode is disabled on the port.
          1 : ISL R_RDY mode is enabled on the port.
          
          Note: This is mutually exclusive with e-port-credit.
          This is mutually exclusive with qos-enabled mode. 
          This is mutually exclusive with long-distance levels.
          ";
      }
      leaf rscn-suppression-enabled {
        if-feature fibrechannel:fibrechannel_switch_platform;
        type uint8 {
          range "0..1";
        }
        description
          "
          Enables or disables Registered State Change Notification (RSCN) 
          suppression on the port.

          0 : Disables RSCN suppression on the port. When disabled, device
              changes on the port generate an RSCN to all other end devices that
              are zoned with this one. By default, RSCN suppression is disabled
              on all ports.
          1 : Enables RSCN suppression on the port. When enabled, any device
              changes on the port do not generate an RSCN to any other end
              device.
          ";
      }
      leaf los-tov-mode-enabled {
        type uint8 {
          range "0..2";
        }
        description
          "
          Enables or disables de-bouncing of signal loss for front-end ports
          for 100 ms.

          0 : LOS_TOV mode is disabled on the port.
          1 : LOS_TOV mode is enabled on fixed-speed ports.
          2 : LOS_TOV mode is enabled on both fixed-speed and auto-negotiated
              ports.
          ";
      }
      leaf npiv-enabled {
		when "port-type-string != 'n-port'";
        type uint8 {
          range "0..1";
        }
        description
          "
          Enables or disables NPIV capability on the port.

          0 : NPIV is disabled on the port.
          1 : NPIV is enabled on the port.
          ";
      }
      leaf npiv-pp-limit {
		when "port-type-string != 'n-port'";
        type int16 {
          range "1..255";
        }
        description
          "
          Configures the maximum number of allowed logins for the port. Valid
          values are 1 to 255.

          1 - 255 : The maximum number of allowed logins for the port.
          ";
      }
      leaf npiv-flogi-logout-enabled {
        type int8 {
          range "0..1";
        }
        config false;
        description
          "
          Whether the base device logout feature is enabled or disabled.

           0 : Base device logout is disabled on the port, which causes the 
               NPIV devices on the same port to log out when the base device 
               logs out.
           1 : Base device logout is enabled on the port. The base device
               can log out without disrupting the NPIV devices on the same port
          ";
      }
      leaf ex-port-enabled {
        if-feature fibrechannel:fibrechannel_switch_platform;
        type uint8 {
          range "0..1";
        }
        description
          "
          Configures the port as an EX_Port.

          0 : The port is not configured as an EX_Port.
          1 : The port is configured as an EX_Port.
          ";
      }
      leaf edge-fabric-id {
        when "../ex-port-enabled = 1";
        type fibrechannel:fabric-id-type;
        description
          "
          Specifies the fabric ID.
          The valid values for FID are from 1 through 128.
          ";
      }
      leaf preferred-front-domain-id {
        when "../ex-port-enabled = 1";
        type fibrechannel:domain-id-type;
        description
          "
          Specifies the preferred domain ID.
          The valid values are 1 to 239.
          ";
      }
      leaf neighbor-switch-ipv4-address {
        when "../ex-port-enabled = 1";
        type inet:ipv4-address;
        config false;
        description
          "
          The IPv4 address of the switch connected to the EX-port. In case of
          trunked EX-Ports, IP address will be available only on the master
          port.
          ";
      }
      leaf neighbor-switch-ipv6-address {
        when "../ex-port-enabled = 1";
        type inet:ipv6-address;
        config false;
        description
          "
          The IPv6 address of the switch connected to the EX-port. In case of
          trunked EX-Ports, IP address will be available only on the master
          port.
          ";
      }
      leaf fec-enabled {
        type int8 {
          range "0..1";
        }
        description
          "
          Whether Forward Error Correction (FEC) is enabled or disabled on 
          a port.

          FEC provides a mechanism for reducing error rates during data
          transmissions over 16 Gbps Fibre Channel links. When FEC is enabled
          on a port, the sender adds systematically generated error-correcting
          code (ECC) to its data transmission. This mechanism allows the
          receiver to detect and correct errors without needing to get
          additional information from the sender.

           0 : FEC is disabled on the port.
           1 : FEC is enabled on the port, and the port is online.

          FEC is supported only at 10 Gbps and 16 Gbps speeds.
          ";
      }
      leaf via-tts-fec-enabled {
        type int8 {
          range "0..1";
        }
        config false;
        description
          "
          Whether FEC negotiation via TTS is enabled or disabled on the port.

           0 : The external control of FEC is disabled.
           1 : The control of the FEC state is permitted via TTS by an 
               externally attached host or device.
          ";
      }
      leaf port-autodisable-enabled {
        type uint8 {
          range "0..1";
        }
        description
          "
          Enables or disables port autodisable on the port, which minimizes 
          traffic disruption introduced in some instances of automatic port 
          recovery. This parameter disables the port when it encounters an 
          event that would cause the port to reinitialize.

          When the autodisable flag is enabled, you can specify the conditions 
          that prevent the port to reinitialize. Such conditions include loss 
          of sync, loss of signal, OLS, NOS, and LIP. Note that a link reset 
          does not cause a port autodisable. When a port is in FICON Management 
          Server (FMS) mode, an autodisabled port remains persistently disabled 
          across High Availability (HA) failover.

          0 : Port autodisable is disabled on the port.
          1 : Port autodisable is enabled on the port.
          ";
      }
      leaf rate-limit-enabled {
        if-feature fibrechannel:fibrechannel_switch_platform;
        type int16 {
          range "0|200|400|600|800|1000|1500|2000|2500|3000|3500|4000|5000|" +
                "7000|8000|9000|10000|11000|12000|13000|14000|15000|16000";
        }
        units "Mbps";
        status obsolete;
        description
          "
          Configures the rate limits in Mbps. This is applicable only with 
          F/FL_Ports. For E/EX_Ports, this resource is not effective. The 
          ingress rate limit is enforced only when a given port can run at a 
          speed higher than the speed specified in the configuration.
          Positive numeric values indicate a rate limit in Mbps.

          0 : No rate limit set.
          ";
      }
      leaf non-dfe-enabled {
        if-feature fibrechannel:fibrechannel_switch_platform;
        type uint8 {
          range "0..1";
        }
        status obsolete;
        description
          "
          Enables or disables non-DFE mode on the port.

          Active receiver DFE uses sophisticated algorithms to automatically
          adjust the receiver to compensate for signal distortions.

            0 : Non-DFE mode is disabled on the port. Automatic receiver 
                adjustment through DFE is activated
            1 : Non-DFE mode is enabled on the port. If the non-DFE enabled port
                is connected to a port that does not require fixed receiver 
                equalization, CRC errors may be detected on the port and the 
                link may toggle.

          Even if disabled, non-DFE is still automatically activated if both of
          following conditions are met: the port speed is 8G or N8 and the
          fillword is IDLE.
	  This is supported only on GEN-5 platforms.
          ";
      }
      
     leaf trunk-port-enabled {
        type uint8 {
          range "0..1";
        }
        description
          "
          Enables or disables trunking on a port.

          0 : Trunking is disabled on the port.
          1 : Trunking is enabled on the port.

          Trunking is enabled by default when a trunking license is present
          on the switch.
          ";
     }
     leaf default-index {
       type fibrechannel:user-port-number-type;
       config false;
       description 
         "
         Default Port Index of the port. The default port index
         can be a port swapped area.
         ";
     }
     leaf physical-state {
       type string {
          length "0..256";
          pattern "(online|offline|testing|faulty|e_port|f_port|segmented|" +
                  "unknown|no_port|no_module|laser_flt|no_light|no_sync|" +
                  "in_sync|port_flt|hard_flt|diag_flt|lock_ref|mod_inv|" +
                  "mod_val|no_sigdet)*";
       }
       config false;
       description
         "The physical state of a port.";
     }
     leaf pod-license-status {
        type boolean;
        config false;
        status deprecated;
        description
          "
          Indicates POD license status for a port.

            true  : The POD license is enabled on the port.
            false : The POD license is disabled on the port.

          Deprecated: Please use 'pod-license-state' instead.
          ";
     }
     leaf pod-license-state {
	   if-feature fibrechannel:fibrechannel_standalone_switch_platform;
        type enumeration {
          enum "reserved" {
            description
            "
            The port is reserved under POD license.
            ";
          }
          enum "released" {
            description
            "
            The port is not reserved under POD license.
            ";
          }
        }
        description
          "
          POD license status of the logical port.
          ";
     }
     leaf index {
       type fibrechannel:user-port-number-type;
        config false;
       description 
         "The user port number of the front-end port.";
     }
     leaf reserved-buffers {
       when "port-type-string != 'fcoe-port' and " +
            "port-type-string != 've-port'and " +
            "port-type-string != 'ethernet-port' and " +
            "../reserved-buffers > 0";
       type uint16 {
         range  "1..max";
       }
	   config false;
       description
         "
         Max amount of buffers or reserved buffers if offline. The value
         increases or decreased when set using the field f-port-buffers
         and is effective when port is online. If port is offline, the
         default value is assigned. The max value is derived from the leaf
         chip-buffers-available. If the value set is too high, it depletes
         the buffers available to other fron end ports on that chip.
         ";
     }
     leaf average-transmit-buffer-usage {
       when "port-type-string != 'fcoe-port' and " +
            "port-type-string != 've-port' and " +
            "port-type-string != 'ethernet-port' and " +
            "../average-transmit-buffer-usage > 0";
       type uint16  {
         range "1..max";
       }
       config false;
       description 
         "
         Average of number of buffers used for transmit per poll period.
         ";
     }
     leaf average-transmit-frame-size {
       when "port-type-string != 'fcoe-port' and " +
            "port-type-string != 've-port' and " +
            "port-type-string != 'ethernet-port' and " +
            "../average-transmit-frame-size > 0";
       type uint16  {
         range "1..max";
	   }
	   config false;
       description
         "
         Average frame size used for transmit including the FC header in bytes.
         ";
     }
     leaf average-receive-buffer-usage {
       when "port-type-string != 'fcoe-port' and " +
            "port-type-string != 've-port' and " +
            "port-type-string != 'ethernet-port' and " +
            "../average-receive-buffer-usage > 0";
       type uint16  {
         range "1..max";
       }
	   config false;
       description 
         "
	       Average of number of buffers used for receive per poll period.
         ";
     }
     leaf average-receive-frame-size {
       when "port-type-string != 'fcoe-port' and " +
            "port-type-string != 've-port' and " +
            "port-type-string != 'ethernet-port' and " +
            "../average-receive-frame-size > 0";
       type uint16 {
         range "1..max";
	   }
	   config false;
       description 
         "
         Average frame size used for receive including the FC header in bytes.
         ";
     }
     leaf current-buffer-usage {
       when "port-type-string != 'fcoe-port' and " +
            "port-type-string != 've-port' and " +
            "port-type-string != 'ethernet-port' and " +
            "../current-buffer-usage > 0";
       type uint16  {
         range "1..max";
       }
       config false;
       description 
          "
          Real time usage of buffers by a front end port.
          ";
     }
     leaf recommended-buffers {
       when "port-type-string != 'fcoe-port' and " +
            "port-type-string != 've-port' and " +
            "port-type-string != 'ethernet-port' and " +
            "../recommended-buffers > 0";
       type uint16  {
          range "1..max";
       }
       config false;
       description
         "
         Real time usage of buffers needed by a port to optimally use a link
         bandwidth. If the value is too less, the port will starve for buffers.
         If too high, buffers would be wasted and not available to other front
         end ports on the same chip.
         ";
     }
     leaf  measured-link-distance {
       when "port-type-string != 'fcoe-port' and " +
            "port-type-string != 've-port' and " +
            "port-type-string != 'ethernet-port'";
       type string {
         length "1..8";
         pattern "[ -~]+";
       }
       units "kilometers";
       config false;
       description 
         "
         Actual link distance measured in kilometers.
         ";
     }
     leaf chip-instance {
       when "port-type-string != 'fcoe-port' and " +
            "port-type-string != 've-port' and " +
            "port-type-string != 'ethernet-port'";
       type uint16 {
	       range "0..7";
       }
       config false;
       description
         "
         The index of the chip on which the given port exists on the chip.
         Typically used for correlating buffers used by a port to the
         corresponding chip.
         ";
     }
     leaf chip-buffers-available {
       when "port-type-string != 'fcoe-port' and " +
            "port-type-string != 've-port' and " +
            "port-type-string != 'ethernet-port'";
       type uint16 {
         range "1..max";
       }
       config false;
       description 
         "
         The front end port on the chip whose available buffer count
         is being queried.
         ";
    }
    leaf port-health {
      type string {
        length  "1..256";
      }
      config false;
      description 
        "
        Information on port health e.g. Offline.
        ";
    }
    leaf authentication-protocol {
      type string {
        length  "1..16";
      }
      config false;
      description
        "
        If authentication is enabled, what authentication protocol 
        is configured on the port.
        ";
    }
    leaf disable-reason {
      when "../is-enabled-state = false";
      type string {
		    length "0..max";
      }
      description
      "
      Textual reason why the port is disabled, either defined by the
      system or by the user. If a user defined reason is set, length
      is limited to 16 characters. Replay of the same value is
      idempotent. Only a user defined reasons can be overwritten via
      REST. One exception, the special system defined value of 'None'
      can be overwritten by a user defined reason. PATCH operations
      with an empty string clears a user defined reason.
      ";
    }

    container areas {
      config false;
      description
        "
        A list of 16 bit areas associated with a Gen7 F-port.
        ";
        leaf-list  area {
        	type fibrechannel:fcid-hex-string-type {
          	  length "6";
        	}
        	description
	          "
		  Area of a device.
		  ";
	}
    }

    leaf  le-domain {
      type uint16 {
	      range "1..128";
      }
      config false;
      description 
        "
        Translate domain ID for the port.
        ";
    }
    leaf port-peer-beacon-enabled {
      type boolean;
      description 
        "
        true : Enabled.
        false : Disabled.
        ";
    }
    leaf clean-address-enabled {
      if-feature fibrechannel:fibrechannel_switch_platform;
      type boolean;
      description
        "
        Enables or disables Clean Address Bit support for the specified
        port. The possible values are:

          true  : Enabled.
          false : Disabled.
        ";
    }
    leaf congestion-signal-enabled {
      when "port-type-string != 'fcoe-port' and " +
           "port-type-string != 've-port' and " +
           "port-type-string != 'ethernet-port'";
      if-feature fibrechannel:fibrechannel_switch_platform;
      type boolean;
      description
        "
        Enables or disables Congestion Signal support for the specified
        port. Only available on Gen7, or later, platforms. The possible
        values are:

          true  : Enabled.
          false : Disabled.
        ";
    }
    leaf segmentation-reason {
      when "../physical-state = segmented";
      type string {
        length  "1..128";
        pattern "[ -~]+";
      }
      config false;
      description
        "
        When a port is segmented, this will display the reason for
        port-segmentation.
        ";
    }
  }
  list fibrechannel-statistics {
      key "name";
      description
        "
        Statistics for all interfaces on the device.

        System-controlled interfaces created by the system are always present
        in this list, whether they are configured or not.
        ";
      leaf name {
        type string {
          /* pattern with 12 slots and 1024 ports separated by a slash */
          pattern "(([1-9]|1[0-9])/([1][0-9][0-9][0-9]|[1-9][1-9][0-9]" +
                  "|[1-9][1-9]|[1-9]))";
        }
        description
          "
          The name of the interface. The slot and port number of the port in 
          the format slot/port.
          ";
      }
      leaf sampling-interval {
        type uint16 {
          range "1..max";
        }
        units "seconds";
        config false;
        description
          "
          The sampling interval in seconds.
          ";
      }
      leaf time-generated {
        type fibrechannel:time-generated-type;
        config false;
        description
          "
          The time at which the statistics were queried.
          ";
      }
      leaf reset-statistics {
        type uint8 {
          range "0..1";
        }
        description
          "Write only leaf. Set to 1 to reset statistical counters.";
      }
      leaf in-octets {
        type yang:zero-based-counter64;
        config false;
        description
          "
          The total number of octets received on the interface, including
          framing characters.
          ";
      }
      leaf out-octets {
        type yang:zero-based-counter64;
        config false;
        description
          "
          The total number of octets transmitted out of the interface, including
          framing characters.
          ";
      }
      leaf in-multicast-pkts {
        type yang:zero-based-counter64;
        config false;
        description
          "
          The number of packets, delivered by this sublayer to a higher
          sublayer, that were addressed to a multicast address at this
          sublayer.  For a MAC-layer protocol, this includes both Group and
          Functional addresses.
          ";
      }
      leaf out-multicast-pkts {
        type yang:zero-based-counter64;
        config false;
        description
          "
          The total number of packets that higher-level protocols requested be
          transmitted and that were addressed to a multicast address at this
          sublayer, including those that were discarded or not sent. For a
          MAC-layer protocol, this includes both Group and Functional
          addresses.
          ";
      }
      leaf in-link-resets {
        type yang:zero-based-counter64;
        config false;
        description
          "
          The number of link resets received.
          ";
      }
      leaf out-link-resets {
        type yang:zero-based-counter64;
        config false;
        description
          "
          The total number of link resets transmitted.
          ";
      }
      leaf in-offline-sequences {
        type yang:zero-based-counter64;
        config false;
        description
          "
          The total number of offline sequences received.
          ";
      }
      leaf out-offline-sequences {
        type yang:zero-based-counter64;
        config false;
        description
          "
          The total number of offline sequences transmitted.
          ";
      }
      leaf invalid-ordered-sets {
        type yang:zero-based-counter64;
        config false;
        description
          "
          The total number of invalid ordered sets received.
          ";
      }
      leaf frames-too-long {
        type yang:zero-based-counter64;
        config false;
        description
          "
          The number of frames received that were longer than 2140 octets. The
          value of 2140 is calculated based on an assumption of 24 header bytes
          plus 4 CRC bytes and 2112 bytes of payload.
          ";
      }
      leaf truncated-frames {
        type yang:zero-based-counter64;
        config false;
        description
          "
          The total number of truncated frames received.
          ";
      }
      leaf address-errors {
        type yang:zero-based-counter64;
        config false;
        description
          "
          Count of frames received with unknown addressing. An example is an
          unknown SID or DID, which are not known to the routing algorithm.
          ";
      }
      leaf delimiter-errors {
        type yang:zero-based-counter64;
        config false;
        description
          "
          Count of invalid frame delimiters that are received at this port. An
          example is a frame with a class 2 at the start and a class 3 at 
          the end.
          ";
      }
      leaf encoding-disparity-errors {
        type yang:zero-based-counter64;
        config false;
        description
          "
          The total number of disparity errors received at this port.
          ";
      }
      leaf too-many-rdys {
        type yang:zero-based-counter64;
        config false;
        description
          "
          The number of instances in which the number of RDYs (readys) 
          exceeded the number of frames received.
          ";
      }
      leaf in-crc-errors {
        type yang:zero-based-counter64;
        config false;
        description
          "
          The number of CRC errors for all frames received.
          ";
      }
      leaf crc-errors {
        type yang:zero-based-counter64;
        config false;
        description
          "
          The number of times that the CRC in a frame does not match the CRC 
          that is computed by the receiver. This count is part of the Link
          Error Status Block (LESB).
          ";
      }
      leaf bad-eofs-received {
        type yang:zero-based-counter64;
        config false;
        description
          "
          The number of bad EOF frames received.
          ";
      }
      leaf encoding-errors-outside-frame {
        type yang:zero-based-counter64;
        config false;
        description
          "
          The number of encoding-error or disparity-error outside frames
          received.
          ";
      }
      leaf multicast-timeouts {
        type yang:zero-based-counter64;
        config false;
        description
          "
          The number of multicast frames that have timed out.
          ";
      }
      leaf in-lcs {
        type yang:zero-based-counter64;
        config false;
        description
          "
          The number of link control frames received.
          ";
      }
      leaf in-frame-rate {
        type yang:zero-based-counter64;
        config false;
        description
          "
          The instantaneous receive frame rate.
          ";
      }
      leaf out-frame-rate {
        type yang:zero-based-counter64;
        config false;
        description
          "
          The instantaneous transmit frame rate.
          ";
      }
      leaf in-max-frame-rate {
        type yang:zero-based-counter64;
        config false;
        description
          "
          The maximum frame receive rate since the last reset.
          ";
      }
      leaf out-max-frame-rate {
        type yang:zero-based-counter64;
        config false;
        description
          "
          The maximum frame transmit rate since the last reset.
          ";
      }
      leaf in-rate {
        type yang:zero-based-counter64;
        config false;
        description
          "
          The instantaneous byte receive rate.
          ";
      }
      leaf out-rate {
        type yang:zero-based-counter64;
        config false;
        description
          "
          The instantaneous byte transmit rate.
          ";
      }
      leaf in-peak-rate {
        type yang:zero-based-counter64;
        config false;
        description
          "
          The peak byte receive rate.
          ";
      }
      leaf out-peak-rate {
        type yang:zero-based-counter64;
        config false;
        description
          "
          The peak byte transmit rate.
          ";
      }
      leaf in-frames {
        type yang:zero-based-counter64;
        config false;
        description
          "
          The number of frames received at this port.
          ";
      }
      leaf out-frames {
        type yang:zero-based-counter64;
        config false;
        description
          "
          The number of frames transmitted from this port.
          ";
      }
      leaf bb-credit-zero {
        type yang:zero-based-counter64;
        config false;
        description
          "
          The number of transitions in and out of the BB credit zero state.
          ";
      }
      leaf input-buffer-full {
        type yang:zero-based-counter64;
        config false;
        description
          "
          The number of transitions in and out of the Input Buffer Full state.
          ";
      }
      leaf f-busy-frames {
        type yang:zero-based-counter64;
        config false;
        description
          "
          The number of F_BSY (fabric busy) frames generated.
          ";
      }
      leaf p-busy-frames {
        type yang:zero-based-counter64;
        config false;
        description
          "
          The number of P_BSY (port busy) frames generated.
          ";
      }
      leaf f-rjt-frames {
        type yang:zero-based-counter64;
        config false;
        description
          "
          The number of F_RJT (fabric frame reject) frames generated.
          ";
      }
      leaf p-rjt-frames {
        type yang:zero-based-counter64;
        config false;
        description
          "
          The number of P_RJT (port frame reject) frames generated.
          ";
      }
      leaf class-1-frames {
        type yang:zero-based-counter64;
        config false;
        description
          "
          The number of Class 1 frames received at this port.
          ";
      }
      leaf class-2-frames {
        type yang:zero-based-counter64;
        config false;
        description
          "
          The number of Class 2 frames received at this port.
          ";
      }
      leaf class-3-frames {
        type yang:zero-based-counter64;
        config false;
        description
          "
          The number of Class 3 frames received at this port.
          ";
      }
      leaf class-3-discards {
        type yang:zero-based-counter64;
        config false;
        description
          "
          The number of Class 3 frames discarded by the port.
          ";
      }
      leaf link-failures {
        type yang:zero-based-counter64;
        config false;
        description
          "
          The number of link failures at this port.
          ";
      }
      leaf invalid-transmission-words {
        type yang:zero-based-counter64;
        config false;
        description
          "
          The number of invalid transmission words received at this port.
          ";
      }
      leaf primitive-sequence-protocol-error {
        type yang:zero-based-counter64;
        config false;
        description
          "
          The number of primitive sequence protocol errors detected at 
          this port.
          ";
      }
      leaf loss-of-signal {
        type yang:zero-based-counter64;
        config false;
        description
          "
          The number of instances of signal loss detected at this port.
          ";
      }
      leaf loss-of-sync {
        type yang:zero-based-counter64;
        config false;
        description
          "
          The number of instances of synchronization loss detected at this port.
          ";
      }
      leaf class3-in-discards {
        type yang:zero-based-counter64;
        config false;
        description
          "
          The number of class 3 receive frames discarded due to timeout.
          ";
      }
      leaf class3-out-discards {
        type yang:zero-based-counter64;
        config false;
        description
          "
          The number of class 3 transmit frames discarded due to timeout.
          ";
      }
      leaf pcs-block-errors {
        type yang:zero-based-counter64;
        config false;
        description
          "
          The number of Physical Coding Sublayer (PCS) block errors. This
          counter records encoding violations on 10 Gbps or 16 Gbps ports.
          ";
      }
      leaf remote-link-failures {
        when "../fibrechannel/operational-status = 2";
        type yang:zero-based-counter64;
        config false;
        description
          "
          The number of link failures at the remote F_Port.
          ";
      }
      leaf remote-invalid-transmission-words {
        when " ../fibrechannel/operational-status = 2";
        type yang:zero-based-counter64;
        config false;
        description
          "
          The number of invalid transmission words received at the remote 
          F_Port.
          ";
      }
      leaf remote-primitive-sequence-protocol-error {
        when "../fibrechannel/operational-status = 2";
        type yang:zero-based-counter64;
        config false;
        description
          "
          The number of primitive sequence protocol errors detected at the 
          remote F_Port.
          ";
      }
      leaf remote-loss-of-signal {
        when "../fibrechannel/operational-status = 2";
        type yang:zero-based-counter64;
        config false;
        description
          "
          The number of instances of signal loss detected at the remote F_Port.
          ";
      }
      leaf remote-loss-of-sync {
        when "../fibrechannel/operational-status = 2";
        type yang:zero-based-counter64;
        config false;
        description
          "
          The number of instances of synchronization loss detected at the remote
          F_Port.
          ";
      }
      leaf remote-crc-errors {
        when "../fibrechannel/operational-status = 2";
        type yang:zero-based-counter64;
        config false;
        description
          "
          The number of frames received with an invalid CRC at the remote 
          F_Port.
          ";
      }
      leaf remote-fec-uncorrected {
        when "../fibrechannel/operational-status = 2";
        type yang:zero-based-counter64;
        config false;
        description
          "
          The counter denotes the number of frames uncorrected by the FEC block 
          at the remote F_Port.
          ";
      }
      container remote-buffer-credit-info {
        when "../fibrechannel/operational-status = 2";
        config false;
        description
          "
          The buffer credit values. Applicable only for the remote F_Port.
          ";
        leaf bb-credit {
          type yang:zero-based-counter64;
          description
            "
            The buffer-to-buffer (BB) credit represents the number of credits
            available to the attached devices.
            ";
        }
        leaf peer-bb-credit {
          type yang:zero-based-counter64;
          description
            "
            The peer port buffer-to-buffer(BB) credit represents the number of
            credits available to the switch port.
            ";
        } 
    } 
    leaf  link-level-interrupts {
      type yang:zero-based-counter64;
      config false;
      description 
        "
	    Count of link level interrupts on the port.
        ";
    }
    leaf  frames-processing-required {
      type yang:zero-based-counter64;
      config false;
      description 
        "
	    Count of frames which required processing on the port.
        ";
    }
    leaf  frames-timed-out {
      type yang:zero-based-counter64;
      config false;
      description 
        "
		Count of frames which  timeout  out during transmit on the port.
        ";
    }
    leaf  frames-transmitter-unavailable-errors {
      type yang:zero-based-counter64;
      config false;
      description 
        "
	    Count of frames which could not be transmitted due to transmitter
		not being available.
        ";
      }
    }

    list extension-ip-interface {
      if-feature fibrechannel:fibrechannel_extension_platform;
      key "name dp-id ip-address";
      description
        "Represents the IP interface defined on extension blade or system.";
      leaf name {
        type brocade-interface-types:ip-extension-interface-type;
        description
          "The name of the interface.";
      }
      leaf dp-id {
        type uint16 {
          range "0..1";
        }
        description
          "
          Extension Data Path Processor ID associated
          with the IP interface. Based on platform either
          it will have a single DP or dual DP. In case of
          single DP only DP0 is supported, and in case of
          dual DP both DP0 and DP1 are supported

          0 : DP0
          1 : DP1.
          ";
      }
      leaf ip-address {
        type inet:ip-address;
        description
          "Specifies the source IPv4/IPv6 address of the interface.";
      }
      leaf ip-prefix-length {
        type brocade-interface-types:ip-prefix-length;
        mandatory true;
        description
          "
          The prefix length operator for the IP address. Once set, prefix length
          cannot be changed.
          ";
      }
      leaf mtu-size {
        type uint16 {
          range "1|1280..9216";
        }
        default "1500";
        description
          "
          Specifies the maximum transmission unit size. The permitted range is
          1280 Bytes to 9216 Bytes or the special value 1 which is equivalent
          to 'auto' mode to  enable PMTU discovery. The discovered value of MTU
          in 'auto' mode can be found as a circuit attribute.
          ";
      }
      leaf vlan-id {
        type uint16 {
          range "0|1..4095";
        }
        default "0";
        description
          "Specifies the VLAN ID. This operand is optional.";
      }
      leaf status-flags {
        type string {
          pattern "(([UBDLPRINMS]|PR|LU) )*";
        }
        config false;
        description
          "
          IP interface Flags:

            U = Up
            B = Broadcast
            D = Debug
            L = Loopback
            P = Point2Point
            R = Running
            I = InUse
            N = NoArp
            PR= Promiscous
            M = Multicast
            S = StaticArp
            LU= LinkUp
          ";
      }
    }

    list gigabitethernet {
      if-feature fibrechannel:fibrechannel_extension_platform;
      key "name";
      description
        "
        The list of gigabitethernet interfaces on the device. System-controlled
        interfaces created by the system are always present in this list,
        whether they are configured or not.
        ";
      leaf name {
        type brocade-interface-types:ge-interface-type;
        description
          "The name of the interface.";
      }
      leaf enabled-state {
        type uint8 {
          range "0..1";
        }
        description
          "
          Enabled or disabled state of the brocade-interface-types:

          0 : Disabled
          1 : Enabled
          ";
      }
      leaf speed {
        type brocade-interface-types:speed-type;
        description
          "
          For PHY types that may operate at various speeds, this leaf allows the
          interface to be forced to operate at a particular speed.  Without any
          explicit configuration, gigabitethernet interfaces run at the
          maximum capable speed.
          ";
      }
      leaf mac-address {
        type yang:mac-address;
        config false;
        description
          "MAC Address for the interface.";
      }
      leaf operational-status {
        type uint16 {
          range "1..2";
        }
        config false;
        description
          "
          Operational status of the port:

          1 : Online
          2 : Offline
          ";
      }
      leaf persistent-disable {
        type uint8 {
          range "0..1";
        }
        description
          "
          Indicates if the port is persistently disabled or persistently enabled

            1 : persistently disabled
            0 : persistently enabled
          ";
      }
      leaf protocol {
        type extension:ge-protocol-type;
        description
          "
          The GE port protocol configuration used by Extension blade/Switch
          during deployment. When GE port protocol is configured for LAN, the 
          GE port is connected on the LAN side for Extending LAN IP traffic 
          over Extension tunnels using IP QOS priorities. When the GE port 
          protocol is configured for WAN then the GE ports are connected on the
          WAN side and are used for configuring the FCIP/Extension tunnels using
          them. In case of chassis system if the slot is powered off or in
          faulty state then the leaf will be skipped in display.

          Supported values:
            LAN : GE port is configured for LAN side connections.
            WAN : GE port is configured for WAN side connections.
          ";
      }
      leaf auto-negotiation-enabled {
        when "../speed = 1000000000";
        type boolean;
        description
          "
          Auto-negotiation is enabled by default in 1G mode. In 10G mode it
          is disabled and not supported. When the port is set for 1G mode,
          you can disable auto-negotiation. In case of chassis system if the
          slot is powered off or in faulty state then the leaf will be skipped
          in display.

          Supported values:
            true : Auto negotiation mode for GE port is enabled.
            false : Auto negotiation mode for GE port is disabled.
          ";
      }
      leaf portchannel-name {
        type string {
          length "0..31";
          pattern "[0-9a-zA-Z_-]*";
        }
        config false;
        description
          "
          The name of the portchannel that the gigabit-ethernet interface
          belongs to. This will be NULL in case the port is not portchannel
          member
          ";
      }
      leaf portchannel-member-timeout {
        when "../portchannel/portchannel-type = dynamic";
        type lag-port-timeout;
        description
        "
        The dynamic portchannel member timeout of the gigabit-ethernet
        interface.
        default long.
        ";
      }
      leaf lldp-profile {
        type string {
          length "0..31";
          pattern "[0-9a-zA-Z_]*";
        }
        description
          "
          LLDP profile name configured on the port.
          Blank lldp-profile means LLDP profile is not configured
          on this port. In such case, lldp global parameters are
          in use for this port.
          To configure a new profile or change existing profile on
          the port, user should perform a PATCH operation with the
          profile name. To remove the profile from the port, user
          should perform a PATCH operation with NULL string.
          ";
      }
      leaf lldp-enabled-state {
        type boolean;
        default true;
        description
        "
        LLDP state of the port
        Possible values are:
          true  - LLDP is enabled on the port
          false  - LLDP is disabled on the port
        ";
      }
      container extension-vlans {
        config false;
        description
          "List of extension vlans configured on this port";
        leaf-list vlan {
          type uint32 {
            range "1..4095";
          }
          description
            "
            Extension vlans configured on this port
            ";
        }
      }
    }

    list gigabitethernet-statistics {
      if-feature fibrechannel:fibrechannel_extension_platform;
      key "name";
      description
        "A list of interface-related statistics for gigabitethernet port.";
      leaf name {
        type brocade-interface-types:ge-interface-type;
        description
          "The name of the interface.";
      }
      leaf out-pkts {
        type yang:zero-based-counter64;
        config false;
        description
          "The total number of packets transmitted out of the interface.";
      }
      leaf out-octets {
        type yang:zero-based-counter64;
        config false;
        description
          "The total number of octets transmitted out of the interface.";
      }
      leaf out-unicast-pkts {
        type yang:zero-based-counter64;
        config false;
        description
          "
          The total number of unicast packets transmitted out of
          the interface.
          ";
      }
      leaf out-multicast-pkts {
        type yang:zero-based-counter64;
        config false;
        description
          "
          The total number of multicast packets transmitted out of the
          interface.
          ";
      }
      leaf out-broadcast-pkts {
        type yang:zero-based-counter64;
        config false;
        description
          "
          The total number of broadcast packets transmitted out of the
          interface.
          ";
      }
      leaf out-vlan-pkts {
        type yang:zero-based-counter64;
        config false;
        description
          "
          The total number of vlan packets transmitted out of the interface.
          ";
      }
      leaf out-pause-pkts {
        type yang:zero-based-counter64;
        config false;
        description
          "
          The total number of pause packets transmitted out of the interface.
          ";
      }
      leaf in-pkts {
        type yang:zero-based-counter64;
        config false;
        description
          "The number of packets received on the interface.";
      }
      leaf in-octets {
        type yang:zero-based-counter64;
        config false;
        description
          "The total number of octets received on the interface.";
      }
      leaf in-unicast-pkts {
        type yang:zero-based-counter64;
        config false;
        description
          "The number of unicast packets received on the interface.";
      }
      leaf in-multicast-pkts {
        type yang:zero-based-counter64;
        config false;
        description
          "The number of multicast packets received on the interface.";
      }
      leaf in-broadcast-pkts {
        type yang:zero-based-counter64;
        config false;
        description
          "The number of broadcast packets received on the interface.";
      }
      leaf in-vlan-pkts {
        type yang:zero-based-counter64;
        config false;
        description
          "The total number of vlan packets received on the interface.";
      }
      leaf in-pause-pkts {
        type yang:zero-based-counter64;
        config false;
        description
          "The total number of pause packets received on the interface.";
      }
      leaf carrier-loss-error {
        type yang:zero-based-counter64;
        config false;
        description
          "The total number of carrier loss errors.";
      }
      leaf crc-error {
        type yang:zero-based-counter64;
        config false;
        description
          "The total number of Cyclic Redundancy Check (CRC) errors.";
      }
      leaf jabber-error {
        type yang:zero-based-counter64;
        config false;
        description
          "The total number of jabber errors.";
      }
      leaf reset-statistics {
        type uint8 {
          range "0..1";
        }
        description
          "Write-only leaf and will not be returned in GET request.
           Set it to 1 to reset statistical counters in PATCH request.";
      }
      leaf time-generated {
        type fibrechannel:time-generated-type;
        config false;
        description
          "The time at which the statistics were queried.";
      }
    }

    list logical-e-port {
      if-feature fibrechannel:fibrechannel_extended_isl;
      key "port-index";
      config false;
      description
        "
        The list of logical E_Port interfaces on the device which form
        the logical inter switch link (lisl). 
        ";
      leaf port-index {
        type fibrechannel:user-port-number-type;
        description
          "
          The unique port number on the switch for identifying a 
          logical E_Port.
          ";
      }
      leaf fabric-id {
        type fibrechannel:fabric-id-type;
        description
          "
          The virtual fabric identification (VFID) of the logical switch
          in which the logical E_Port is created.
          ";
      }
      leaf operational-status {
        type enumeration {
          enum "online" {
            description
            "
            The logical E-Port is online.
            ";
          }
          enum "offline" {
            description
            "
            The logical E-Port is offline.
            ";
          }
        }
        description
          "
          Operational status of the the logical E_Port.
          ";
      }
      leaf offline-reason {
        when "operational-status = offline";
        type enumeration {
          enum "Init" {
            description
            "
            The logical E-Port is initializing.
            ";
          }
          enum "CreateRequestSent" {
            description
            "
            Request to create a logical E-Port is sent to the peer switch.
            ";
          }
          enum "CreatReqRtryPendg" {
            description
            "
            Retry pending to send create request to peer switch.
            ";
          }
          enum "PeerLSDown" {
            description
            "
            Peer switch is disabled or offline.
            ";
          }
          enum "CreateFailed" {
            description
            "
            Logical E-Port creation failed.
            ";
          }
          enum "PeerReqInProcess" {
            description
            "
            Request from peer switch to create logical E-Port in process.
            ";
          }
          enum "PeerReqReceived" {
            description
            "
            Request from peer switch to create logical E-Port received.
            ";
          }
          enum "DeleteSent" {
            description
            "
            Delete logical E-port sent to peer switch.
            ";
          }
          enum "Invalid" {
            description
            "
            Logical E-Port in Invalid state.
            ";
          }
        }
        description
          "
          Reason for logical E_Port Offline status.
          ";
      }
      leaf neighbor-node-wwn {
        type fibrechannel:wwn-type;
        description
          "
          The  neighbor node WWN logically connected to this port.
          ";
      }
      container associated-physical-ports {
        description
          "
          Associated physical E_Port list.
          ";
        leaf-list port {
          type fibrechannel:slot-port-name-type;
          description
            "
            Physical port number of base switch associated with logical E_Port.
            ";
        }
      }
    }
    list portchannel {
      if-feature fibrechannel:portchannel_platform;
      key "name";
      description
        "
        The list of portchannel interfaces on the switch, their
        related configuration and operational state.
        ";
      leaf name {
        type string {
          length "1..31";
          pattern "[0-9a-zA-Z_-]+";
        }
        description
          "The portchannel name.";
      }
      leaf key {
        type uint32 {
          range "1..1000";
        }
        description
          "
          The portchannel key. The portchannel key cannot be modified once
          the portchannel is created. If user does not provide the key
          during portchannel creation, the system will auto-assign an
          available key. The portchannel key is unique across all portchannel
          interfaces on the switch.
          ";
      }
      leaf portchannel-type {
        type portchannel-type;
        description
          "
          The type of a portchannel interface. Portchannel Type is a
          mandatory parameter while the portchannel is created.

          Possible values:
          static   : Static portchannel type.
          dynamic  : Dynamic portchannel type.
          ";
      }
      leaf speed {
        type brocade-interface-types:portchannel-speed-type;
        config false;
        description
          "
          The speed of the portchannel interface.
          The speed of the portchannel is the speed of its member ports.
          speed is an read-only parameter of a port-channel.

          Note: The speed of all members of a portchannel must match.
          ";
      }
      leaf lacp-system-mac-address {
        type ietf:mac-address;
        config false;
        description
          "The LACP MAC address of the system.";
      }
      leaf admin-state-enabled {
        type  boolean;
        default "true";
        description
          "
          Indicates the admin state of the portchannel.
          The possible values are:

            false : portchannel is  disabled.
            true  : portchannel is enabled.
          ";
      }
      leaf auto-negotiation-enabled {
        when "../speed = 1000000000";
        type  boolean;
        description
          "
          Indicates the auto-negotiation of the FCIP portchannel.
          The possible values are:

            false : auto-negotiation is off.
            true  : auto-negotiation is on.
          ";
      }
      leaf operational-status-enabled {
        type  boolean;
        config false;
        description
          "
          The portchannel operational status. The possible values are:

            false : portchannel is offline.
            true  : portchannel is online.
          ";
      }
      container gigabit-ethernet-member-ports {
        description
          "The Gigabit Ethernet portchannel members.";
        leaf-list port {
          type brocade-interface-types:ge-interface-type;
          description
            "
            The list of gigabit ethernet interfaces that are members of
            the portchannel.
            ";
        }
      }
      leaf primary-member-gigabit-ethernet-port {
        when "../type = dynamic";
        type brocade-interface-types:ge-interface-type;
        config false;
        description
          "The primary member interface of the portchannel.";
      }
    }
  }
}
