module brocade-operation-extension {

  yang-version 1.1;
  namespace "urn:brocade.com:mgmt:brocade-operation-extension";
  prefix brocade-operation-extension;
  
  import "brocade-extension-types" {
    prefix extension;
  }

  import fibrechannel-yang-types {
    prefix fibrechannel;
  }

  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    This module contains a collection of YANG definitions for Extension
    operations on a switch.

    Copyright © 2020 Broadcom. All rights reserved. The term 'Broadcom' refers
    to Broadcom Inc. and/or its subsidiaries.
    ";

  revision 2020-01-06 {
    description
      "
      Fabric OS 9.0.0
      ---------------
        Initial release
      ";
    reference
      "None";
  }

  rpc extension {
    description
      "
      The RPC command definition for Extension operation on a Brocade
      switch.
      ";
    input {
      container extension-operation-parameters {
        if-feature fibrechannel:fibrechannel_extension_platform;
        description
          "The extension operation input container.";
        leaf slot {
          type uint16 {
            range "0..12";
          }
          description
            "
            The slot number of for the datapath processor.
            ";
        }
        leaf config-clear {
          when "not(../config-default) and not(../global-lan-statistics-reset)";
          type boolean;
          description
          "
          Clear the extension configuration for the switch or blade.

          The config clear operation may be disruptive in nature.
            switch : A switch needs to be rebooted after a config clear
	     operation, without which future config operations  will be
	     blocked.
            blade  : A blade needs to be powered off before clearing the
             slot corresponding configuration.

          Supported values:

          false: No operation
          true : Clear the extension configuration.
          ";
        }
        leaf config-default {
          when "not(../config-clear) and not(../global-lan-statistics-reset)";
          type boolean;
          description
          "
          Default the extension configuration for the switch or blade.
          The config default operation is a disruptive operation and details
          are as below.
            switch : After successful operation the switch
              automatically reboots.
            blade  : A blade should be in online state for the operation
              to be allowed and the blade may be slot powered off and on
              to allow different extension modes to be applied correctly.
          Supported values:
            false: No operation
            true : Default the extension configuration.
            ";
        }
        leaf global-lan-statistics-reset {
          when "not(../config-clear) and not(../config-default)";
          type boolean;
          description
          "
          Reset the global LAN statistics on a DP.

          Supported values:
            false: No operation
            true : Reset the global LAN statistics.
          ";
        }
        leaf dp-id {
          when "../global-lan-statistics-reset = true";
          type extension:dp-id-type;
          description
            "
            Extension Data Path Processor ID. Based on platform
            either it will have a single DP or dual DP. In case of
            single DP only DP0 is supported, and in case of
            dual DP both DP0 and DP1 are supported

            0 : DP0
            1 : DP1.
            ";
        }

      }
    }
    output {
      container extension-operation-status {
        if-feature fibrechannel:fibrechannel_extension_platform;
        description
          "The container for Extension  operation status";
        leaf  status-message {
          type string {
            length "1..1024";
            pattern "[ -~]+";
          }
          description 
            "
            The status message informing the operation status
            ";
        }
      }
    }
  }
}
