module brocade-fibrechannel-diagnostics {

  yang-version 1.1;
  namespace "urn:brocade.com:mgmt:brocade-fibrechannel-diagnostics";
  prefix diag;

  import ietf-yang-types {
    prefix yang;
  }

  import fibrechannel-yang-types {
    prefix fibrechannel;
  }

  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    This module defines the YANG module 'fibrechannel-diagnostics', which
    provides fibre channel port diagnostics.

    Copyright © 2020 Broadcom. All rights reserved. The term 'Broadcom' refers
    to Broadcom Inc. and/or its subsidiaries.
    ";

  revision 2020-11-23 {
    description
      "
        Fabric OS 8.2.0a
        ----------------
          Correction of 'payload' leaf type and pattern

        Fabric OS 8.2.1
        ---------------
          Formatting
          Organization information
          Correction of fraction precision
          Default statement removed
          Naming standard update.

        Fabric OS 9.0.0
        ---------------
          Addition of 'remote-switch-wwn' and 'remote-port-index' leaf
          attributes to 'brocade-fibrechannel-diagnostics' container.
          Updated the 'payload' leaf description.
          Updated link error stats enum values.
          Updated the description for leafs tx,rx,loss,comments in the
          containers egress-power-loss and ingress-power-loss.
          Updated the description for leaf frame-size.
          Added two new leafs to support individual test start and
          estimated time.
          Updated following: leaf 'name' with pattern, leafs 'tx,rc,loss' in the
          containers ingress-power-loss and egress-power-loss with range and
          the typedef 'comments-type' with length, pattern and description.
          Updated length for leaf comments in the containers ingress-power-loss
          and egress-power-loss.
          Updated patterns for the leaf 'name,''start-time' and 'end-time.'

        Fabric OS 9.0.1
        ---------------
          Corrected typos
          Updated pattern for the 'comments' leaf of ingress-power-loss and
          egress-power-loss containers.
          Update pattern for the leaf 'end-time.'
      ";
    reference
      "None";
  }

  typedef result-type {
    type string {
      length "1..64";
      pattern "NOT STARTED|PASSED|SKIPPED|FAILED|IN PROGRESS|" +
              "RESPONDER|STOPPED|UNKNOWN";
    }
    description
      "
      Result is the completion status of the test. Valid values are:

         NOT STARTED
         PASSED
         SKIPPED
         FAILED
         IN PROGRESS
         RESPONDER
         STOPPED
         UNKNOWN
      ";
  }

  typedef comments-type {
    type string {
      length "0..256";
      pattern "^$|Test failed|No SFP or chip support|See remote port results|" +
              "Remote port is not ready to start the test|" +
              "Too many offline events|Remote port test failed|" +
              "Remote port WWN changed|Slot or port offline|" +
              "Protocol error|Unable to start/restart the test|" +
              "D-Port mode mismatch, Not D-Port|Module removed|" +
              "No remote SFP or chip support|" +
              "No remote port support or skipped|" +
              "E_WRAP/O_WRAP set failed|User opted to skip|" +
              "Test skipped due to SFP loopback error|Test timed out";
    }
    description
      "
      Comments are additional textual information elaborating on the completion
      status when test is skipped or fails. It will return an empty string if no
      comments are available. The valid comments include:

           Test failed
           No SFP or chip support
           See remote port results
           Remote port is not ready to start the test
           Too many offline events
           Remote port test failed
           Remote port WWN changed
           Slot or port offline
           Protocol error
           Unable to start/restart the test
           D-Port mode mismatch, Not D-Port
           Module removed
           No remote SFP or chip support
           No remote port support or skipped
           E_WRAP/O_WRAP set failed
           User opted to skip
           Test skipped due to SFP loopback error
           Test timed out
      ";
  }

  typedef error-stats-type {
    type enumeration {
      enum "none" {
        description
          "Errors were not detected on the port.";
      }
      enum "generic" {
        description
          "Generic error encountered in test.";
      }
      enum "enc-in" {
        description
          "Encoding errors inside of frames.";
      }
      enum "crc-err" {
        description
          "Frames with CRC errors.";
      }
      enum "trunc-frame" {
        description
          "Frames shorter than minimum.";
      }
      enum "frame-too-long" {
        description
          "Frames longer than maximum.";
      }
      enum "bad-eof" {
        description
          "Frames with bad end-of-frame.";
      }
      enum "enc-out" {
        description
          "Encoding error outside of frames.";
      }
      enum "bad-os" {
        description
          "Invalid ordered set.";
      }
      enum "c3-discard" {
        description
          "Class 3 frames discarded.";
      }
      enum "rx-c3-timeout" {
        description
          "Class 3 receive frames discarded due to timeout.";
      }
      enum "tx-c3-timeout" {
        description
          "Class 3 transmit frames discarded due to timeout.";
      }
      enum "unroutable" {
        description
          "Frames that are unroutable.";
      }
      enum "unreachable" {
        description
          "Frames with unreachable destination.";
      }
      enum "other-discard" {
        description
          "Other C3 frame discards.";
      }
      enum "link-failure" {
        description
          "Link failures.";
      }
      enum "sync-loss" {
        description
          "Loss of synchronizations.";
      }
      enum "signal-loss" {
        description
          "Loss of signal.";
      }
      enum "prim-seq-proto" {
        description
          "Primitive sequence protocol error.";
      }
      enum "inv-tx-word" {
        description
          "Invalid transmit frames.";
      }
      enum "invalid-crc" {
        description
          "Crc error with good eof.";
      }
      enum "delimiter-err" {
        description
          "Frame delimiter errors.";
      }
      enum "addr-id-err" {
        description
          "Address ID errors.";
      }
      enum "link-reset-in" {
        description
          "Link resets received.";
      }
      enum "link-reset-out" {
        description
          "Link resets transmitted.";
      }
      enum "port-ols-in" {
        description
          "OLS primitives received.";
      }
      enum "port-ols-out" {
        description
          "OLS primitives transmitted.";
      }
      enum "inv-arb" {
        description
          "Invalid ARB.";
      }
      enum "single-credit-loss" {
        description
          "Single vcrdy/frame loss on link.";
      }
      enum "multi-credit-loss" {
        description
          "Multiple vcrdy/frame loss on link.";
      }
      enum "fec-uncorrected" {
        description
          "FEC uncorrected errors.";
      }
      enum "pcs-block-error" {
        description
          "PCS block errors.";
      }
      enum "unknown-error" {
        description
          "Maximum number of error stats.";
      }
    }
    description
      "Displays error stats on the port, if any.";
  }

  container brocade-fibrechannel-diagnostics {
    description
      "
      Performs the following diagnostics:

        An electrical loopback test (supported only on 16Gb and 32Gb SFPs
        capable of electrical loopback)

        An optical loopback test (supported only on 16Gb and 32Gb SFPs
        capable of optical loopback)

        A link traffic test

        A link distance measurement

      Support is only for dynamic d-port.
      ";
    list fibrechannel-diagnostics {
      key "name";
      description
        "
        The list of ports on the device.

        System-controlled interfaces created by the system are always present in
        this list, whether they are configured or not.
        ";
      leaf name {
        type string {
          length "1..32";
          pattern "(^([0-9]|1[0-9])/(10[0-2][0-9]|" +
                  "[1-9][0-9][0-9]|[1-9][0-9]|[0-9])$)";
        }
        description
          "
          The name of the interface. The slot and port number of the port
          (slot/port). Maximum of 12 slots and maximum of 1024 ports.
          ";
      }
      leaf diagnostic-control {
        type uint32 {
          range "0..2";
        }
        description
          "
          Manually terminate the test, re-initiate the test, or stop the test on
          a diagnostic port (D Port).

            0    : Stop - terminates the diagnostics on the D Port
            1    : Start - initiates the diagnostics on the D Port
            2    : Restart - restarts the D Port diagnostic tests with the
                        configured parameters

          This option is not supported for D Port HBA connections.
          NOTE: write-only leaf node and would not be present in GET request.
          ";
      }
      leaf mode {
        type enumeration {
          enum "manual" {
            description
              "Test started manually (manually restarted using CLI or API).";
          }
          enum "automatic" {
            description
              "
              Test started automatically (initiated due to port online event).
              ";
          }
        }
        config false;
        description
          "
          The testing mode. Indicates whether the test was started manually or
          automatically.
          ";
      }
      leaf state {
        type string {
          length "1..64";
          pattern "PASSED|FAILED|FAILED (Protocol error)|" +
                  "FAILED (Unable to start/restart the test)|" +
                  "SKIPPED|IN PROGRESS|NOT STARTED|STOPPED";
        }
        config false;
        description
          "
          On the link initiator, this field displays the overall test status as
          PASSED, FAILED, FAILED (Protocol error), Unable to start/restart the
          test, SKIPPED, IN PROGRESS, NOT STARTED, or STOPPED. On the link
          responder, the status displays PASSED, FAILED, STOPPED, or RESPONDER.
          ";
      }
      leaf distance {
        type int32 {
          range "-1..max";
        }
        units "meter";
        config false;
        description
          "
          The estimated physical distance of the inter-switch link in meters.
          The Link distance for SPFs or ICL ports which do not support E_WRAP
          and O_WRAP have a precision of +/- 50 meters for 8 Gbps LWL SFPs,
          8 Gbps ELWL SFPs, 10 Gbps SFPs, ICL ports, and +/- 5 meters for
          16 Gbps SFPs.

             -1 : indicates an unknown distance
          ";
      }
      leaf remote-switch-wwn {
        type fibrechannel:wwn-type;
        config false;
        description
          "
          The WWN of the remote switch connected to this D-Port.
          ";
      }
      leaf remote-port-index {
        type fibrechannel:user-port-number-type;
        config false;
        description
          "
          The user port index of the remote port connected to this D-Port.
          ";
      }
      container electrical-loopback-test {
        config false;
        description
          "
          An electrical loopback test; Supported only on 16 Gb and 32 Gb SFPs
          capable of electrical loopback.
          ";
        leaf result {
          type result-type;
          description
            "Result is the completion status of the test. ";
        }
        leaf comments {
          type comments-type;
          description
            "
            Comments are additional textual information elaborating on the
            completion status when test is skipped or fails.
            ";
        }
        leaf start-time {
          type fibrechannel:time-24hr-extended-type;
          description
            "Electrical loopback test start time.";
        }
        leaf estimate-time {
          type fibrechannel:time-24hr-extended-type;
          description
            "Estimated completion time of electrical loopback test.";
        }
      }
      container optical-loopback-test {
        config false;
        description
          "
          An optical loopback test; Supported only on 16 Gb and 32 Gb SFPs
          capable of optical loopback.
          ";
        leaf result {
          type result-type;
          description
            "Result is the completion status of the test. ";
        }
        leaf comments {
          type comments-type;
          description
            "
            Comments are additional textual information elaborating on the
            completion status when test is skipped or fails.
            ";
        }
        leaf start-time {
          type fibrechannel:time-24hr-extended-type;
          description
            "Optical loopback test start time.";
        }
        leaf estimate-time {
          type fibrechannel:time-24hr-extended-type;
          description
            "Estimated completion time of optical loopback test.";
        }
      }
      container link-traffic-test {
        config false;
        description
          "The link traffic test.";
        leaf result {
          type result-type;
          description
            "Result is the completion status of the test. ";
        }
        leaf comments {
          type comments-type;
          description
            "
            Comments are additional textual information elaborating on the
            completion status when test is skipped or fails.
            ";
        }
        leaf start-time {
          type fibrechannel:time-24hr-extended-type;
          description
            "Link traffic test start time.";
        }
        leaf estimate-time {
          type fibrechannel:time-24hr-extended-type;
          description
            "Estimated completion time of link traffic test.";
        }
      }
      leaf start-time {
        type string {
          pattern '[a-zA-Z]+\s[a-zA-Z]+\s\d{2}\s\d{2}:\d{2}:\d{2}\s\d{4}';
        }
        config false;
        description
          "Time diagnostics started.";
      }
      leaf frame-count {
        when "not(../time)";
        type yang:counter32 {
          range "1..65535";
        }
        units "million";
        description
          "
          Number of frames sent for link traffic test (default is 1 million
          frames).

          Note: This is mutually exclusive with the 'time' leaf.
          ";
      }
      leaf frame-size {
        type uint32 {
          range "36..2112";
        }
        units "byte";
        description
          "
           The test frame size in bytes (default is 1024 bytes).
           The size of the frames should be given in multiples of 4; otherwise
           the nearest higher multiple of 4 value will be taken as frame size.
          ";
      }
      leaf time {
        when "not(../frame-count)";
        type string {
          length "1..8";
          pattern "([0-9]{2}:[0-5][0-9])";
        }
        description
          "
          How long the test should run in the format hh:mm, where hh is hours
          and mm is minutes.

          Note: This is mutually exclusive with the 'frame-count' leaf.
          ";
      }
      container payload-pattern {
        description
          "The user-defined payload pattern.";
        leaf pattern {
          // payload and payload are mutually exclusive
          when "not(../payload)";
          type string {
            length "1..32";
            pattern "BYTE_NOT|QUAD_NOT|WORD_NOT|BYTE_RAMP|QUAD_RAMP|" +
                    "WORD_RAMP|BYTE_LFSR|RANDOM|CRPAT|CSPAT|CHALF_SQ|" +
                    "CQTR_SQ|RDRAM_PAT|jCRPAT|jCJTPAT|jCSPAT|PRED_RAND|" +
                    "SMI_TEST|CJPAT|QUAD_NOTP|JSPAT|JTSPAT";
          }
          description
            "
            The name of the predefined industry pattern names used for frame
            traffic test. The valid patterns are:

                  BYTE_NOT
                  QUAD_NOT
                  WORD_NOT
                  BYTE_RAMP
                  QUAD_RAMP
                  WORD_RAMP
                  BYTE_LFSR
                  RANDOM
                  CRPAT
                  CSPAT
                  CHALF_SQ
                  CQTR_SQ
                  RDRAM_PAT
                  jCRPAT
                  jCJTPAT
                  jCSPAT
                  PRED_RAND
                  SMI_TEST
                  CJPAT
                  QUAD_NOTP
                  JSPAT
                  JTSPAT
            ";
        }
        leaf payload {
          // payload and pattern are mutually exclusive
          when "not(../pattern)";
          type string {
            length "1..10";
            pattern "(0[xX])?[0-9a-fA-F]{1,8}";
          }
          description
            "
            Specifies the user defined payload .
            Payload should be in the range of 0x1-0xffffffff.
            ";
        }
      }
      container fec {
        description
          "
          Enables Forward Error Correction (FEC) for diagnostic testing. This
          option is not supported on ports configured with Dense Wavelength
          Division Multiplexing (DWDM)
          ";
        leaf enable {
          type enumeration {
            enum "no" {
              description
                "FEC is disabled.";
            }
            enum "yes" {
              description
                "FEC is enabled.";
            }
          }
          description
            "
            When FEC is enabled on a port, the sender adds systematically
            generated error-correcting code (ECC) to its data transmission.
            This mechanism allows the receiver to detect and correct errors
            without needing to get additional information from the sender.

            This leaf only supports enabling FEC.
            ";
        }
        leaf active {
          type enumeration {
            enum "no" {
              description
                "FEC is not active.";
            }
            enum "yes" {
              description
                "FEC is active";
            }
          }
          config false;
          description
            "
            The FEC state can be active or inactive. An active FEC state
            indicates that FEC is enabled and actually running. An inactive
            state can indicate two conditions: FEC is enabled, but not running
            due to some error condition (for example, FEC may not be enabled on
            both ends of the link). Or FEC is disabled and therefore inactive.
            ";
        }
        leaf option {
          type enumeration {
            enum "no" {
              description
                "FEC is not used in D-Port tests.";
            }
            enum "yes" {
              description
                "FEC is used in D-Port tests";
            }
          }
          config false;
          description
            "
            The option indicates that D-Port diagnostic test is using FEC
            feature or not.
            ";
        }
      }
      leaf rt-latency {
        type uint32;
        units "nanoseconds";
        config false;
        description
          "
          The round trip link latency in nanoseconds or unknown when the test is
          in progress.  Round trip link latency is the time required for the
          light to travel from a given port to the port at the remote side of
          the link and back again.
          ";
      }
      leaf buffers-required {
        type string;
        config false;
        description
          "
          The  number of buffers required for the given distance and speed.
          Irrespective of test frame size, the number of buffers required is
          calculated for 2112-byte frames.
          ";
      }
      leaf end-time {
        type string {
          pattern '^$|[a-zA-Z]+\s[a-zA-Z]+\s\d{2}\s\d{2}:\d{2}:\d{2}\s\d{4}';
        }
        config false;
        description
          "The date and time that the diagnostic test ended.";
      }
      container cr {
        description
          "The Credit Recovery (CR) status.";
        leaf enable {
          type enumeration {
            enum "no" {
              description
                "Credit Recovery is disabled.";
            }
            enum "yes" {
              description
                "Credit Recovery is enabled.";
            }
          }
          description
            "
            The Credit Recovery enables credits or frames to be recovered.
            This leaf only supports enabling Credit Recovery.
            ";
        }
        leaf active {
          type enumeration {
            enum "no" {
              description
                "Credit Recovery is not active.";
            }
            enum "yes" {
              description
                "Credit Recovery is active.";
            }
          }
          config false;
          description
            "Credit Recovery is active.";
        }
        leaf option {
          type enumeration {
            enum "no" {
              description
                "Credit Recovery (CR) is not used in D-Port tests.";
            }
            enum "yes" {
              description
                "Credit Recovery (CR) is used in D-Port tests";
            }
          }
          config false;
          description
            "
            The leaf option indicates whether the D-Port diagnostic test is
            using Credit Recovery (CR).
            ";
        }
      }
      container failure-report {
        config false;
        description
          "Displays details on the local port and remote port errors, if any,";
        leaf errors-detected-local {
          type enumeration {
            enum "no" {
              description
                "Errors were not detected on the local port.";
            }
            enum "yes" {
              description
                "Errors were detected on the local port.";
            }
          }
          status deprecated;
          description
            "
             Displays details on the local port, if any.

             Deprecated: Please use 'failure-report-local-details'
             leaf-list instead.
            ";
        }
        leaf errors-detected-remote {
          type enumeration {
            enum "no" {
              description
                "Errors were not detected on the remote port.";
            }
            enum "yes" {
              description
                "Errors were detected on the remote port.";
            }
          }
          status deprecated;
          description
            "
             Displays details on the remote port, if any.

             Deprecated: Please use 'failure-report-remote-details'
             leaf-list instead.
            ";
        }
      }
      container failure-report-local-errors {
        config false;
        description
          "Displays details on the local port errors.";
        leaf-list error {
          type error-stats-type;
            description
              "Displays error stats name on the local port, if any.";
        }
      }
      container failure-report-remote-errors {
        config false;
        description
          "Displays details on the remote port errors.";
        leaf-list error {
          type error-stats-type;
            description
              "Displays error stats name on the remote port, if any.";
        }
      }
      container egress-power-loss {
        config false;
        description
          "
          The power values and power loss in the transmit path. The following
          values are displayed:

          power  transmitted from the local side of the link (Tx)
          power received on the remote side of the link (Rx), the power loss,
          that is, the relative difference in power (Diff), and the status of
          the power loss
          (No Loss, within tolerable limits, and outside tolerable limits).
          ";
        leaf tx {
          type decimal64 {
            fraction-digits 2;
            range "-9.99..9.99";
          }
          units "dBm";
          description
            "
            Power transmitted from the local side of the link (Tx).
            In this case, if D-port test is failing or not yet started Tx
            value might not be available. In such case this leaf is not 
            displayed.
            ";
        }
        leaf rx {
          type decimal64 {
            fraction-digits 2;
            range "-9.99..9.99";
          }
          units "dBm";
          description
            "
            Power received on the remote side of the link (Rx).
            In this case, if D-port test is failing or not yet started Rx
            value might not be available. In such case this leaf is not
            displayed.
            ";
        }
        leaf loss {
          type decimal64 {
            fraction-digits 2;
            range "-9.99..9.99";
          }
          description
            "
            The power loss, that is, the relative difference in power (Diff).
            This leaf is not displayed if the value is not available.";
        }
        leaf comments {
          type string {
            length "0..256";
            pattern "^$|No Loss|Cable power loss is within tolerable limit|" +
                    "Cable power loss is outside tolerable limit";
          }
          description
            "
            Status of the power loss (No Loss, within tolerable limits, and
            outside tolerable limits). This leaf returns an empty string if 
            the value is not available.
            ";
        }
      }
      container ingress-power-loss {
        config false;
        description
          "
          The power values and power loss in the receive path. The following
          values are displayed:

          power received on the local side of the link (Rx),
          power transmitted from the remote side of the link (Tx),
          the power loss, that is, the relative difference in power (Diff),
          and the status of the power loss
          (No  Loss,  within  tolerable limits, and outside tolerable limits).
          ";
        leaf tx {
          type decimal64 {
            fraction-digits 2;
            range "-9.99..9.99";
          }
          description
            "
            Power transmitted from the remote side of the link (Tx).
            In this case, if D-port test is failing or not yet started
            Tx value might not be available. In such case this leaf is not
            displayed.
            ";
        }
        leaf rx {
          type decimal64 {
            fraction-digits 2;
            range "-9.99..9.99";
          }
          description
            "
            Power received on the local side of the link (Rx).
            In this case, if D-port test is failing or not yet started Rx
            value might not be available. In such case this leaf is not
            displayed.
            ";
        }
        leaf loss {
          type decimal64 {
            fraction-digits 2;
            range "-9.99..9.99";
          }
          description
            "
            The power loss, that is, the relative difference in power (Diff).
            This leaf is not displayed if the value is not available.
            ";
        }
       leaf comments {
          type string {
            length "0..256";
            pattern "^$|No Loss|Cable power loss is within tolerable limit|" +
                    "Cable power loss is outside tolerable limit";
          }
          description
            "
            Status of the power loss (No Loss, within tolerable limits, and
            outside tolerable limits). This leaf returns an empty string if
            the value is not available.
            ";
        }
      }
    }
  }
}
