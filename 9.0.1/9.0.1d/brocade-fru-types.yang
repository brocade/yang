module brocade-fru-types {

  yang-version 1.1;
  namespace "urn:brocade.com:mgmt:brocade-fru-types";
  prefix fru;

  import ietf-inet-types {
    prefix inet;
  }

  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    This module contains the collection of fru YANG types.

    Copyright © 2020 Broadcom. All rights reserved. The term 'Broadcom' refers
    to Broadcom Inc. and/or its subsidiaries.
    ";

  revision 2020-11-06 {
    description
      "
      Initial release (FOS 8.2.1).

      Refine descriptions.
      Fabric OS 9.0.1
      ---------------
        Updated pattern for leaf serial-number-type
        and part-number-type
      ";
    reference
      "None";
  }

  typedef ip-gateway-type {
    type union {
      type inet:ip-address;
      type string {
        length "1";
        pattern "[*]";
      }
    }
    description
      "
      Specifies the IP address of an IP router that can
      route packets to the destination IP address. This attribute can
      contain '*' while retrieving route entries which are created
      internally by the system.
      ";
  }
  typedef manufacturer-type {
    type string {
      length "1..63";
      pattern "[ -~]*";
    }   
    description
      "
      The name of the organization responsible for producing the blade.
      ";
  }
  typedef operational-state-type {
    type string {
      length "2..60";
      pattern "faulty|ok|below minimum|above maximum|absent|" +
              "unknown|not ok";
    }
    description
      "
      The current operational state of the Fru.
      The state 'not ok' displays when the unit is faulty for
      an unknown reason.
      ";
  }
  typedef part-number-type {
    type string {
      length "0..16";
      pattern "[ -~]{0,16}";
    }
    description
      "
      The part number assigned by the organization responsible for
      producing or manufacturing the PhysicalElement.
      ";
  }
  typedef serial-number-type {
    type string {
      length "0..16";
      pattern "[ -~]{0,16}";
    }
    description
      "
      The serial-number resource contains a Printable ASCII String that
      specifies the serial number of the chassis
      ";
  }
  typedef power-detail-type {
    type int32 {
      range "-1000..-1";
    }
    description
       "
       The power details such as the maximum power consumption allocated
       or consumed by the fru.
       ";
  }
  typedef time-detail-type {
    type uint32 {
      range "0..10000";
    }
    description
       "
       The time details such as the number of days the FRU has been powered
       on or was last powered on.
       ";
  }
  typedef firmware-version-type {
    type string {
      length "1..255";
      pattern "[ -~]{1,255}";
    }
    description
       "
       A human readable string identifying the firmware version running
       on the switch.
       ";
  }
  typedef state-type {
    type enumeration {
      enum "inserted" {
        description
          "Indicates fru is inserted.";
      }
      enum "removed" {
        description
          "Indicates fru is removed.";
      }
      enum "invalid" {
        description
          "Indicates the invalid state of the fru.";
      }
    }
    description
      "
      It indicates the fru state.
      ";
  }
  typedef sensor-category {
    type enumeration {
      enum "temperature" {
        description
          "Indicates type temperature sensor of the fru.";
      }
    }
    description
      "
      It indicates type of fru sensor.
      ";
  }
  typedef fru-type {
    type enumeration {
      enum "sw blade" {
        description
          "Indicates fru is switch blade.";
      }
      enum "cp blade" {
        description
          "Indicates fru is cp blade.";
      }
      enum "core blade" {
        description
          "Indicates fru is core blade.";
      }
      enum "application blade" {
        description
          "Indicates fru is application blade.";
      }
      enum "fan" {
        description
          "Indicates fru is fan.";
      }
      enum "wwn" {
        description
          "Indicates fru is wwn card.";
      }
      enum "power supply" {
        description
          "Indicates fru is power supply.";
      }
      enum "unknown" {
        description
          "Indicates unknown fru.";
      }
    }
    description
      "
      It indicates the fru type.
      ";
  }
}
