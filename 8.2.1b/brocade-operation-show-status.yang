module brocade-operation-show-status {

  yang-version 1.1;
  namespace "urn:brocade.com:mgmt:brocade-operation-show-status";
  prefix show-status;

  import  brocade-operation-types {
    prefix operation;
  }

  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    This module defines the YANG module 'show-status' which provides
    all details about the status of any REST operation.
          
    Brocade Proprietary and Confidential.
    Copyright © 2018 Brocade Communications Systems LLC.
    All Rights Reserved.
    
    BROCADE HIGHLY CONFIDENTIAL TRADE SECRET INFORMATION
 
    Access or possession of this material grants you no right or license,
    express, implied, statutory or otherwise, under any Brocade patent,
    copyright, trade secret right or other intellectual property right.
    Any such license must be contained in a written license agreement
    signed by an authorized officer of Brocade.  Additionally, access or
    possession of this material is limited to Brocade employees with a
    need to know or named employees of Brocade vendors authorized by
    Brocade in writing to access this material.
    
    Restricted Rights: Use, duplication, or disclosure by the U.S.
    Government is subject to restrictions of FAR 52.227-19 and its
    successors, or (c)(1)(ii) of the Rights in Technical Data and
    Computer Software clause at DFAR 252.227-7013 and its successors.
    ";

  revision 2018-08-03 {
    description
      "
      FOS 8.2.1
      -----
      Initial release for operation support.
      Refine descriptions.
      ";
    reference
      "None";
  }

  rpc show-status {
    description 
      "
      The RPC asynchronous operation status based on the input message ID.
      ";

    input {
      leaf message-id {
        type operation:message-id-type;
        mandatory true;
        description 
          "
          The input message ID which is required to retrieve the associated
          operation status. 
          ";
      }
    }
    output {
      uses operation:show-status-group;
    }
  }
}
