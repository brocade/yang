module brocade-logging-types {

  yang-version 1.1;
  namespace "urn:brocade.com:mgmt:brocade-logging-types";
  prefix brocade-logging-types;

  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    This module defines the YANG module 'brocade-logging-types',
    which has the type definitions for 'brocade-logging' module

    Copyright © 2019 Broadcom. All rights reserved. The term 'Broadcom' refers to
    Broadcom Inc. and/or its subsidiaries.
    ";

  revision 2018-07-06 {
    description
      "Initial release (FOS 8.2.1).";
    reference
      "None";
  }
  
  typedef severity-level-type {
    type string {
      length "4..8";
      pattern "info|warning|error|critical";
    }
    description
      "The type of severity levels.";
  }

  typedef message-id-type {
    type string {
      length "7..12";
      pattern "[0-9A-Z]{2,7}-[0-9]{4,4}";
    }
    description
      "Message ID Type for the raslog.";
  }

  typedef ascii-text-type {
    type string {
      pattern "[ -~]*";
    }
    description
      "The type of text.";
  }

  typedef module-id-type {
    type string {
      length "2..7";
      pattern "[0-9A-Z]{2,7}";
    }
    description
      "The type of FOS module-id.";
  }

  typedef time-24hr-type {
    type string {
      length "0|5";
      pattern "([0-2][0-9]:[0-5][0-9])?";
    }
    description
      "
      Specifies time. Time is in 24 hour clock format HH:MM

        HH : Hours [00 to 23],
        MM : Minutes [00 to 59].
      ";
  }

  typedef class-type {
    type string {
      length "2..13";
      pattern "zone|security|configuration|firmware|fabric|ls|cli|maps";
    }
    description
      "
      Represents type of log need to be collected i.e. fabric related log
      etc.
      ";
  }

  typedef event-class-type {
    type enumeration {
      enum "zone" {
        description
          "
          Log generated by zone module.
          ";
      }
      enum "security" {
        description
          "
          Log generated by security module.
          ";
      }
      enum "configuration" {
        description
          "
          Log generated by configuration event.
          ";
      }
      enum "firmware" {
        description
          "
          Log generated by firmware event.
          ";
      }
      enum "fabric" {
        description
          "
          Log generated by fabric event.
          ";
      }
      enum "ls" {
        description
          "
          Log generated by logical switch module.
          ";
      }
      enum "cli" {
        description
          "
          Log generated by CLI.
          ";
      }
      enum "maps" {
        description
          "
          Log generated by MAPS module.
          ";
      }
      enum "ras" {
        description
          "
          Log generated by RAS module.
          ";
      }
      enum "system" {
        description
          "
          Log generated by system event.
          ";
      }
    }
    description
      "
      Class type of event that generated log.
      ";
  }
}
