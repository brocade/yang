module fibrechannel-yang-types {

  yang-version 1.1;
  namespace "urn:brocade.com:params:xml:ns:brocade:fibrechannel-yang-types";
  prefix fibrechannel-yang-types;

  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    This module contains a collection of generally useful derived YANG data
    types.

    Copyright © 2019 Broadcom. All rights reserved. The term 'Broadcom' refers to
    Broadcom Inc. and/or its subsidiaries.

    ";

  reference
    "
    ANSI INCITS 433-2006, Fibre Channel - Link Services (FC-LS).

    ANSI INCITS 463-2010, Fibre Channel - Generic Services - 6 (FC-GS-6).

    ANSI INCITS 511-2016, Fibre Channel - Switch Fabric - 6 (FC-SW-6).

    ANSI INCITS 545-20xx, Fibre Channel - Framing and Signaling - 5
    (FC-FS-5).
    ";

  revision 2018-07-06 {
    description
      "
      Fabric OS 8.2.1b
      ----------------
      Refine descriptions.
      
      Fabric OS 8.2.1
      ----------------
        Added types:
          brocade-hex-string-type
          fcid-hex-string-type
          port-type-string-type
          user-port-number-type

        Deprecated types:
          fcid-type

        Added features:
          feature access_gateway_platform
          fibrechannel_switch_platform
          fibrechannel_chassis_platform

        Formatting
        Organization information
      ";
    reference
      "None";
  }

  typedef brocade-hex-string-type {
    type string {
      length "0..514";
      pattern "0[xX][0-9a-fA-F]*";
    }
    description
      "
      Brocade hexadecimal string format
      ---------------------------------
      This type defines a generic case-insensitive hexadecimal string that
      requires a '0x' prefix (also case-insensitive).  Modules that use this
      type may refine the length to a lower value, if needed.
      ";
  }

  typedef wwn-type {
    type string {
      length "0..24";
      pattern "([0-9a-fA-F]{2}(:[0-9a-fA-F]{2}){7})";
    }
    description
      "
      A 64-bit identifier, with a 60-bit value preceded by a 4-bit
      Network_Address_Authority Identifier, used to identify entities in
      Fibre Channel (e.g., Nx_Port, node, F_Port, or Fabric).

      Fibre channel WWN (16 hex digits with the colon separator).

      For example:
            11:22:33:44:55:66:77:88
      ";
  }

  typedef domain-id-type {
    type uint32 {
      range "0..239";
    }
    description
      "Fibre Channel switch domain identifier. Value of zero indicates
       segmented link.";
  }

  typedef fcid-type {
    type uint32 {
      range "0..16777215";
    }
    status deprecated;
    description
      "
      Fibre channel ID (FCID), decimal format.

      Deprecated: Please use 'fcid-hex-string-type' instead.
      ";
  }

  typedef fcid-hex-string-type {
    type string {
      length "8";
      pattern "0[xX][0-9a-fA-F]*";
    }
    description
      "
      Definition of the Fibre Channel address for an Nx_Port
      (FCID), hexadecimal format. The format allows for six
      hexadecimal digits prefixed by '0x' or '0X'.

      For example:

        0x010200

      ";
  }

  typedef fabric-id-type {
    type uint32 {
      range "1..128";
    }
    description
      "Fabric ID (FID)";
  }

  typedef time-generated-type {
    type uint32 {
      range "1..2147483646";
    }
    units "seconds";
    description
      "
      The time at which the statistics were queried. This value specified the
      time since epoch in seconds.
      ";
  }

  typedef fc4-type-type {
    type string {
      length "0..512";
      pattern "(0[xX][0-9a-fA-F]{2}| |IPFC|FCP|FCP-Features|SATA-Tunnel|" +
              "SBCCS|SBCCS-Channel|SBCCS-Control-Unit|FC-CT|FC-SW|FC-IFR|" +
              "FC-NVMe|HIPPI-FP|MIL-STD-1553|ASM|FC-VI|Application-Services|" +
              "Generic-FC-Features|RNID-Topology-Discovery)*";
    }
    description
      "
      A space-delimited string of FC-4 types:

      IPFC                      (0x05)
      FCP                       (0x08)
      FCP-Features              (0x0A)
      SATA-Tunnel               (0x14)
      SBCCS                     (0x18)
      SBCCS-Channel             (0x1B)
      SBCCS-Control-Unit        (0x1C)
      FC-CT                     (0x20)
      FC-SW                     (0x22)
      FC-IFR                    (0x25)
      FC-NVMe                   (0x28)
      HIPPI-FP                  (0x40)
      MIL-STD-1553              (0x48)
      ASM                       (0x49)
      FC-VI                     (0x58)
      Application-Services      (0x60)
      Generic-FC-Features       (0xDE)
      RNID-Topology-Discovery   (0xDF)
      0xnn                      (Unknown/Reserved <hexadecimal value>)
      ";
  }

  typedef fc4-features-type {
    type string {
      length "0..512";
      pattern "( |FCP-Initiator|FCP-Target|FC-NVMe-Discovery-Service|" +
              "FC-NVMe-Initiator|FC-NVMe-Target)*";
    }
    description
      "The registered FC-4 Features in relation to a given FC-4 Type.";
  }

  typedef speed-type {
    type string {
      length "0..512";
      pattern "( |bit-[0-9]{1,2}|speed-1-gfc|speed-2-gfc|speed-10-gfc|" +
              "speed-4-gfc|speed-8-gfc|speed-16-gfc|speed-32-gfc|" +
              "speed-20-gfc|speed-40-gfc|speed-128-gfc|speed-64-gfc|" +
              "speed-256-gfc|speed-not-established|speed-10-ge|" +
              "speed-40-ge|speed-100-ge|speed-25-ge|speed-50-ge|" +
              "speed-400-ge)*";
    }
    description
      "
      The possible Fibre Channel transmission speeds:

      speed-1-gfc           (Mask Value (hex): 0000 0001)
      speed-2-gfc           (Mask Value (hex): 0000 0002)
      speed-10-gfc          (Mask Value (hex): 0000 0004)
      speed-4-gfc           (Mask Value (hex): 0000 0008)
      speed-8-gfc           (Mask Value (hex): 0000 0010)
      speed-16-gfc          (Mask Value (hex): 0000 0020)
      speed-32-gfc          (Mask Value (hex): 0000 0040)
      speed-20-gfc          (Mask Value (hex): 0000 0080)
      speed-40-gfc          (Mask Value (hex): 0000 0100)
      speed-128-gfc         (Mask Value (hex): 0000 0200)
      speed-64-gfc          (Mask Value (hex): 0000 0400)
      speed-256-gfc         (Mask Value (hex): 0000 0800)
      speed-not-established (Mask Value (hex): 0000 8000)
      speed-10-ge           (Mask Value (hex): 0001 0000)
      speed-40-ge           (Mask Value (hex): 0002 0000)
      speed-100-ge          (Mask Value (hex): 0004 0000)
      speed-25-ge           (Mask Value (hex): 0008 0000)
      speed-50-ge           (Mask Value (hex): 0010 0000)
      speed-400-ge          (Mask Value (hex): 0020 0000)
      bit-n                 (Unknown/Reserved <bit position>)
      ";
  }

  typedef port-type-string-type {
    type string {
      length "0..64";
      pattern "0[xX][0-9a-fA-F]{2}|n-port|nl-port|f/nl-port|" +
              "nx-port|f-port|fl-port|e-port|b-port|a-port";
    }
    description
      "
      n-port    (0x01)
      nl-port   (0x02)
      f/nl-port (0x03)
      nx-port   (0x7F)
      f-port    (0x81)
      fl-port   (0x82)
      e-port    (0x84)
      b-port    (0x85)
      a-port    (0x86)
      0xnn      (Unknown/Reserved <hexadecimal value>)
      ";
  }

  typedef class-of-service-type {
    type string {
      length "0..256";
      pattern "( |bit-[4-9]|bit-[1-2][0-9]|bit-3[0-1]|class-f|" +
              "class-1|class-2|class-3)*";
    }
    description
      "
      A string representation of the Class of Service bit-field (see FC-SW).

      Bit 0 - Class F
        Represented as 'class-f'

      Bit 1 - Class 1
        Represented as 'class-1'

      Bit 2 - Class 2
        Represented as 'class-2'

      Bit 3 - Class 3
        Represented as 'class-3'

      Bit 4 - obsolete
        Represented as 'bit-4'

      Bit 5: reserved
        Represented as 'bit-5'

      Bit 6 - obsolete
        Represented as 'bit-6'

      Bits 7 to 31: reserved
        Represented as 'bit-7' though 'bit-31', respectively
      ";
  }

  typedef slot-port-name-type {
    type string {
      length "0..32";
      /* pattern with 12 slots and 1024 ports separated by a slash */
      pattern "(([1-9]|1[0-9])/([1][0-9][0-9][0-9]|[1-9][1-9][0-9]|" +
              "[1-9][1-9]|[1-9]))";
    }
    description
      "
      Typically the name of the interface.  The slot and port number of the
      port (slot/port).
      ";
  }

  typedef user-port-number-type {
    type int32 {
      range "0..3400";
    }
    description
      "Fibre Channel port user port number.";
  }
  typedef octet-member-index-type {
	type int8 {
	  range "0..7";
    }
    description
      "Used to identify which member in the octet for a given trunk.";
  }
  typedef deskew-type {
    type uint16 {
      range "1..255";
    }
	units "10ns";
    description 
       "Time in 10ns units. Used by trunking for fibrechannel ports.";
  }
  typedef percentage-type {
    type string {
      length  "1..6";
        pattern "([0-9][0-9].[0-9][0-9]|100.00)";
      }
      description 
        "Percentage string up to two decimal places.";
  }
  
  feature access_gateway_platform {
    description
      "
      Indicates that the fibrechannel access-gateway mode is supported

      This feature is mutually exclusive with the
      'fibrechannel_switch_platform' feature.
      ";
  }

  feature fibrechannel_switch_platform {
    description
      "
      Indicates that the fibrechannel switch native mode is supported

      This feature is mutually exclusive with the
      'access_gateway_platform' feature.
      ";
  }

  feature fibrechannel_chassis_platform {
    if-feature fibrechannel_switch_platform;
    description
      "
      Indicates that the fibrechannel chassis features like 256 Area Limit
      are supported.
      
      This feature requires the switch to be in Native mode, that is the
      feature 'fibrechannel_switch_platform' has to be supported.

      This feature is mutually exclusive with the
      'access_gateway_platform' feature.
      ";
  }
}
