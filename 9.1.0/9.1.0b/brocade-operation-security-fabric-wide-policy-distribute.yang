module brocade-operation-security-fabric-wide-policy-distribute {

  yang-version 1.1;
  namespace
"urn:brocade.com:mgmt:brocade-operation-security-fabric-wide-policy-distribute";
  prefix brocade-operation-security-fabric-wide-policy-distribute;
  
  import "brocade-security-yang-types" {
    prefix brocade-security-type;
  }
  
  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    This module contains a collection of YANG definitions for 
    managing security related policies in fabric wide.

    Copyright © 2020 Broadcom. All rights reserved. The term 'Broadcom' refers
    to Broadcom Inc. and/or its subsidiaries.
    ";

  revision 2021-11-19 {
    description
      "
      
      Fabric OS 9.1.0
      ---------------
        Initial release
      
      ";
    reference
      "None";
  }
  rpc security-fabric-wide-policy-distribute {
    description
      "
      The RPC command definition for setting the fabric-wide consistency
      policy.
      ";
    input {
      container distribute-parameters {
        description
          "
          Parameters for setting the fabric-wide consistency policy.
          ";
        container policy-types {
          description
            "
            Security database(s) to be distributed.
            ";
          leaf-list type {
            type brocade-security-type:fabric-wide-consistency-policy-type;
            description
              "
              All members specified in a given policy set are automatically
              distributed to all participating switches in the fabric that
              support the policy. 
              ";
          }
        }
      }
    }
  }
}
