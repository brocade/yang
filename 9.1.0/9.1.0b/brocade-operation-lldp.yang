module brocade-operation-lldp {

  yang-version 1.1;
  namespace "urn:brocade.com:mgmt:brocade-operation-lldp";
  prefix brocade-lldp;

  import fibrechannel-yang-types {
    prefix fibrechannel;
  }

  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    The 'brocade-operation-lldp' YANG module provides the means for following
    lldp port-related operations
    1. Clearing lldp neighbor 
    2. Resetting lldp statistics

    Copyright © 2020 Broadcom. All rights reserved. The term 'Broadcom' refers
    to Broadcom Inc. and/or its subsidiaries.
    ";

  revision 2021-04-28 {
    description
      "
      Fabric OS 9.0.0
      ---------------
        Initial release

      Fabric OS 9.1.0
      ---------------
        Added support for physical management interfaces
        Refined descriptions
      ";
    reference
      "None";
  }

  rpc lldp {
    description
      "
      The RPC command definition for LLDP port operations
      on a Brocade switch.
      ";
    input {
      container lldp-operations {
        description
          "The LLDP actions container.";
        leaf slot-port {
          when "not(../cp-name) and not(../physical-interface)";
          type fibrechannel:slot-port-name-type;
          description
            "The port number in slot/port format.";
        }
        leaf cp-name {
          when "not(../slot-port)";
          type fibrechannel:cp-name-type;
          description
            "
             For a fixed-port switch, the valid name is cp0.
             For a chassis switch, the valid names are cp0 and cp1.
            ";
        }
        leaf physical-interface	{
          when "not(../slot-port)";
          type fibrechannel:physical-interface-type;
          description
            "The physical management iterface name.
             For a fixed-port switch, the valid name is eth0.
             For a chassis switch, the valid names are eth0 and eth3.
            ";
        }
        leaf action {
          type enumeration {
            enum "clear-neighbor" {
              description
                "Clears the LLDP neighbor details for the specified port.";
            }
            enum "reset-statistics" {
              description
                "Resets the LLDP-related statistics for the specified port.";
            }
          }
          description
            "The LLDP actions on the specified port.";
        }  
      } 
    }
  }
}
