module brocade-operation-security-authentication-secret {

  yang-version 1.1;
  namespace
    "urn:brocade.com:mgmt:brocade-operation-security-authentication-secret";
  prefix brocade-operation-security-authentication-secret;
  
  import "brocade-security-yang-types" {
    prefix brocade-security-type;
  }
  
  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    This module contains a collection of YANG definitions for configuring and
    managing authentication secrets on a switch.

    Copyright © 2020 Broadcom. All rights reserved. The term 'Broadcom' refers
    to Broadcom Inc. and/or its subsidiaries.
    ";

  revision 2021-11-19 {
    description
      "
      
      Fabric OS 9.1.0
      ---------------
        Initial release
      
      ";
    reference
      "None";
  }
  rpc security-authentication-secret {
    description
      "
      The RPC command definition for configuring shared secrets for DH-CHAP
      authentication.
      ";
    input {
      list authentication-secret-parameters {
        description
          "
          Manages the DH-CHAP shared secret key database used for
          authentication.
          ";
        leaf member {
          type brocade-security-type:security-input-type;
          description
            "
              Switch or node for which shared secret to be configured.
              Values can be switch name or switch WWN or domain ID or node WWN.
              In Access Gateway mode, only a WWN is allowed.
              Wildcard (*) is allowed only for remove. Use this value to remove
              all secret pair entries in the switch.
            ";
        }
        leaf peer-secret {
          when "../action = set";
          type brocade-security-type:authentication-secret-type;
          description
            "
            The secret of the peer that authenticates peer. The secret must
            be encoded with the Base64 encoding scheme.
            ";
        }
        leaf local-secret {
          when "../action = set";
          type brocade-security-type:authentication-secret-type;
          description
            "
            The local secret that authenticates peer. The local and peer secret
            should not be the same. The secret must be encoded with the Base64
            encoding scheme.
            ";
        }
        leaf action {
          type brocade-security-type:authentication-secret-action-type;
          description
            "
            The action to Manage the DH-CHAP shared secret key information.
            Available actions include: 
            o set
            o remove
            ";
        }
      }
    }
  }
}
