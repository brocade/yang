module brocade-fru {

  yang-version 1.1;
  namespace "urn:brocade.com:mgmt:brocade-fru";
  prefix brocade-fru;

  import ietf-inet-types {
    prefix inet;
  }
  import brocade-fru-types {
    prefix fru;
  }
  import ietf-yang-types {
    prefix yang;
  }
  import fibrechannel-yang-types {
    prefix fibrechannel;
  }

  organization
    "Broadcom Inc.";

  contact
    "
    Address:

      1320 Ridder Park Road
      San Jose, CA 95131
      USA

    Support:

      https://www.broadcom.com/support/fibre-channel-networking/

    Website:

      https://www.broadcom.com/products/fibre-channel-networking/software/

    ";

  description
    "
    This module defines the YANG module 'brocade-fru', which provides a
    detailed view of configuration and runtime information of the FRU's
    blade, Fan and PS details.
     
    Copyright © 2021 Broadcom. All rights reserved. The term 'Broadcom' refers
    to Broadcom Inc. and/or its subsidiaries.
    ";

  revision 2021-10-19 {
    description
      "
      Fabric OS 8.2.1
      ---------------
      Initial release (FOS 8.2.1).
      Refine descriptions.

      Fabric OS 9.0.0
      ---------------
        Updating the extension config related fields for config default
        and config clear support

      Fabric OS 9.0.1
      ---------------
        Updated description of leaf power-usage

      Fabric OS 9.1.0
      ---------------
        Deprecate existing IP management interface configuration leafs.
        Add IP management interface leafs for static, DHCP, DHCPv6 and
        Auto configurations
        Add vendor-id leaf in wwn list
        Support new typedef 'product-name-type' for 'model-name' leaf in blade
        list.
        Added grouping fru-vendor-detail-group.
        Update ipv6-prefix and ip-prefix support
        Updated leaf input-voltage range
        Updated leaf manufacture-date
        Deprecated attribute fru-time-detail-group under
        wwn list and marked it as status obsolete
        and used leaf's 'time-alive-in-hours' and
        'time-awake-in-hours' instead.
        The FRU sensor temperature value '0' indicates 'Not Available'.
        Updated leaf air-flow-direction-type
      ";
    reference
      "None";
  }
  
  typedef air-flow-direction-type {
    type string {
      length "1..255";
      pattern "forward (non-portside exhaust)|non-portside exhaust|" +
              "reverse (non-portside intake)|non-portside intake|" +
              "not available|not applicable";
    }
    description
      "
      The air flow direction of the fan.
      ";
  }
  grouping fru-part-serial-number-group {
    description
       "
       It defines the group of leafs associated with the operation.
       ";
      leaf part-number {
        type fru:part-number-type;
        config false;
        description
          "
          The part number assigned by the organization responsible
          for producing or manufacturing the blade.
          ";
      }
      leaf serial-number {
        type fru:serial-number-type;
        config false;
        description
          "
          The serial-number resource contains a printable ASCII string that
          specifies the serial number of the chassis.
          ";
      }
  }
  grouping fru-time-detail-group {
    description
       "
       It defines the group of leafs associated with the operation.
       ";
      leaf time-alive {
         type fru:time-detail-type;
         units "days";
         config false;
         description
           "
           The number of days the FRU has been powered on.
           ";
      }
      leaf time-awake {
         type fru:time-detail-type;
         units "days";
         config false;
         description
           "
           The number of days since the FRU was last powered on.
           ";
      }
  }
  grouping fru-vendor-detail-group {
    description
       "
       It defines the group of leafs associated with the operation.
       ";
      leaf vendor-serial-number {
        type string {
          length "0..20";
          pattern "[ -~]{0,20}";
        }
        config false;
        description
          "
          The serial number of the chassis assigned by the vendor.
          ";
      }
      leaf vendor-part-number {
        type string {
          length "0..20";
          pattern "[ -~]{0,20}";
        }
        config false;
        description
          "
          The part number of the chassis assigned by the vendor.
          ";
      }
      leaf vendor-revision-number {
        type string {
          length "0..4";
          pattern "[ -~]{0,4}";
        }
        config false;
        description
          "
          The revision number of the chassis assigned by the vendor.
          ";
      }
      leaf vendor-id {
        type string {
          length "0..10";
          pattern "[ -~]*";
        }
        config false;
        description
          "
          The identifier of the chassis assigned by the vendor.
          ";
      }
  }
  container brocade-fru {
    description
       "
       Configuration and runtime information of the FRUs installed in the 
       chassis. 
       ";
    list blade {
      key "slot-number";
      description
        "
        A list of blade details for the specified slot number.
        ";

      leaf slot-number {
        type uint16 {
         range "0..12";
        }
        description
          "
          The number of the physical slot in the chassis in which the 
          blade is inserted.
          ";
      }
      leaf manufacturer {
        type string {
          length "1..63";
          pattern "[ -~]*";
        }
        config false; 
        description
          "
          The name of the blade manufacturer.
          ";
      }
      leaf blade-type {
        type string {
          length "1..32";
          pattern "[ -~]{1,32}"; 
        }
        config false; 
        description
          "
          The type of blade (sw blade, cp blade, core blade, ap blade).
          ";
      }
      leaf blade-id {
        when "../blade-type != 'unknown'";  
        type uint16 {
          range "1..1000";
        }
        config false; 
        description
          "
          The ID of the blade.
          "; 
      }
      leaf blade-state {
        type string {
          length "1..255";
          pattern "[ -~]{1,255}";
        }
        config false; 
        description
          "
          The current state of the blade.
          ";
      }
      leaf model-name {
        when "../blade-type != 'unknown' or ../slot-number != 0";
        type fibrechannel:product-name-type;
        config false; 
        description
          "
          A printable ASCII string that describes the model of the blade.
          ";
      }
      leaf firmware-version {
        type fru:firmware-version-type;
        config false; 
        description
          "
          A human-readable string that displays the firmware version running on
          the switch. For an AP blade, it displays the AP blade firmware 
          version. For other blades, it displays the active CP firmware version.
          ";
      }   
      leaf fc-port-count {
        when "../blade-type != 'cp blade' or ../blade-type != 'unknown'";
        type uint16 {
           range "0..256";
        }
        config false; 
        description
          "
          The number of FC ports supported by the blade.
          ";
      }
      leaf ge-port-count {
        when "../extension-enabled = true or ../blade-id = 75";
        type uint16 {
           range "0..256";
        }
        config false; 
        description
          "
          The number of GE ports supported by the blade.
          ";
      }
      container ip-address-list {
        when "../blade-type = 'cp blade'";
        config false;
        status deprecated;
        description
          "
          A list of IP addresses assigned to the CP blade.

          Deprecated: Please use 'static-ip-addresses' and
          'stateful-ip-addresses' leafs in brocade-fru instead.
          ";
        leaf-list ip-address {
          type union {
            type inet:ip-address;
            type inet:ip-prefix;
          }
          description
            "
            List of IP addresses assigned to the CP blade.
            This parameter is applicable only for CP blades.
            ";
        }
      }
      container static-ip-addresses {
        when "../blade-type = 'cp blade'";
        description
          "
          A list of out-of-band static IPv4 and IPv6 addresses assigned
          to the ethernet port of CP blade.
          ";
        leaf-list ip-address {
          type inet:ip-address;
          description
            "
            List of static IP addresses assigned to the ethernet port of
            CP blade. This parameter is applicable only for CP blades.
            ";
        }
      }   
      container stateful-ip-addresses {
        when "../blade-type = 'cp blade'";
        config false;
        description
          "
          List of out-of-band DHCP and DHCPv6 addresses assigned to the ethernet
          port of CP blade.
          ";
        leaf-list ip-address {
          type union {
            type inet:ip-address;
            type inet:ip-prefix;
          }
          config false;
          description
            "
            List of out-of-band stateful IP addresses assigned to the ethernet
            port of CP blade. This parameter is applicable only for CP blades.
            ";
        }
      }
      container stateless-ipv6-addresses {
        when "../blade-type = 'cp blade'";
        config false;
        description
          "
          List of out-of-band stateless IPv6 addresses assigned to the ethernet
          port of CP blade.
          ";
        leaf-list ip-address {
          type union {
            type inet:ipv6-address;
            type inet:ipv6-prefix;
          }
          config false;
          description
            "
            List of out-of-band stateless IP addresses assigned to the ethernet
            port of CP blade. This parameter is applicable only for CP blades.
            ";
        }
      }
      leaf link-local-address {
        when "../blade-type = 'cp blade'";
        type union {
          type inet:ipv6-address;
          type inet:ipv6-prefix;
        }
        config false;
        description
          "
          IPv6 Link local address of CP blade. This parameter is applicable
          only for CP blades.
          ";
      }
      container ip-gateway-list {
        when "../blade-type = 'cp blade'";
        config false;
        status deprecated;
        description
          "
          A list of gateway IP address of the CP blade.

          Deprecated: Please use 'static-ip-gateways', 'dhcp-gateway'
          and 'stateless-ip-gateways' leafs in
          brocade-management-ip-interface instead.
          ";
        leaf-list ip-gateway {
          type fru:ip-gateway-type;
          description
            "
            The list of gateway IP addresses of an IP router that
            can route packets to the destination IP address. The gateway
            address must be on the same IP subnet as one of the port
            IP addresses. This parameter is applicable only for CP blades.
            ";
        }
      }
      leaf subnet-mask {
        when "../blade-type = 'cp blade'";
        type inet:ipv4-address;
        config false;
        status deprecated;
        description
          "
          The IPv4 subnet mask of the switch IP network.
          This parameter is applicable only for CP blades.

          Deprecated: Please use 'static-subnet-mask' and 'dhcp-subnet-mask'
          in brocade-fru instead.
          ";
      }
      leaf primary-firmware-version {
        when "../blade-type = 'cp blade'";
        type fru:firmware-version-type;
        config false; 
        description
          "
          A human-readable string that identifies the firmware version running
          on the primary partition of the CP blade.
          ";
      }   
      leaf secondary-firmware-version {
        when "../blade-type = 'cp blade'";
        type fru:firmware-version-type;
        config false; 
        description
          "
          A human readable string that identifies the firmware version running
          on the secondary partition of the CP blade.
          ";
      }
      leaf power-consumption {
         type fru:power-detail-type;
         units "watts";
         config false;
         description
           "
           The maximum power consumption allocated for the blade.
           ";
      }
      leaf power-usage {
         type fru:power-detail-type;
         units "watts";
         config false;
         description
           "
           The real-time power consumed by the FRU.
           ";
      }
      leaf extension-enabled {
        type boolean;
        config false; 
        description
          "
          Indicates whether the switch or blade supports extension.
          For blade ID's 154, 186, and 213 the value is set to true.

          false : Extension is not supported.
          true  : Extension is supported.
          ";
      }
      leaf extension-app-mode {
        when "../extension-enabled = true";
        type string {
          length "4..11";
          pattern "FCIP|hybrid|unavailable";
        }
        description
          "
          The application mode configuration of the extension blade or switch.
          Note that the application mode configuration change is a disruptive 
          operation and that when the configuration change is successful, one 
          of the following actions occur:

            switch : A switch automatically reboots.
            blade  : A blade automatically powers off and on.

          Blade ID 213 supports only hybrid mode.
          For blade ID 154 and 186, the default is FCIP mode.
          For blade ID 213, the default is hybrid mode.

          Supported modes:

            FCIP        : Supports FCIP-only tunnels.
            hybrid      : Supports FCIP with IPEXT tunnels.
            unavailable : The value is unavailable at the moment. This is 
                          read-only value and can be seen in specific scenarios
                          where the information is not loaded because of slot 
                          power off or slot faulty after reboot or powercycle.
          ";
      }
      leaf extension-ve-mode {
        when "../extension-enabled = true";
        type string {
          length "4..14";
          pattern "not applicable|10VE|20VE|unavailable";
        }
        description
          "
          The VE mode configuration of the extension blade or switch. Note that 
          a VE mode configuration change is a disruptive operation and that 
          when the configuration change is successful, one of the following 
          actions occur:

            switch : A switch automatically reboots.
            blade  : A blade automatically powers off and on.

          For blade ID 154 and 186, the default is 10VE mode.
          For blade ID 213, the default is not applicable.

          Supported modes:

            not applicable : Not a supported configuration. 
            10VE : 10 VEs available for tunnel configuration (5 VE_Ports 
                   per DP).
            20VE : 20 VEs available for tunnel configuration (10 VE_Ports 
                   per DP).
            unavailable : The value is unavailable at the moment. This is a 
                          read-only value and can be seen in specific scenarios
                          where the information is not loaded because of slot 
                          power off or slot faulty after reboot or powercycle.
          ";
      }
      leaf extension-ge-mode {
        when "../extension-enabled = true";
        type string {
          length "4..14";
          pattern "not applicable|copper|optical|unavailable";
        }
        description
          "
          The GE mode configuration of the extension blade or switch.
          In copper mode, the RJ-45 ports (ge0 and ge1) are enabled and optical 
          ports (ge2 and ge3) are disabled. 
          In optical mode, the optical ports (ge2 and ge3) are enabled and the 
          RJ45 ports (ge0 and ge1) are disabled.

          For blade ID 154 and 186, the default is not applicable.
          For blade ID 213, the default is optical.

          Supported modes:

            not applicable : Not a supported configuration.
            optical : ge2 and ge3 use the first two optical ports.
            copper  : ge0 and ge1 use front end RJ45 ports.
            unavailable : The value is unavailable at the moment. This is 
                          read-only value and can be seen in specific scenarios 
                          where the information is not loaded because of slot 
                          power off or slot faulty after reboot or powercycle.
          ";
      }
      leaf manufacture-date {
        if-feature fibrechannel:fibrechannel_chassis_platform;
        type fru:fru-date-type;
        config false;
        description
          "
          The FRU manufacture date.
          ";
      }
      leaf  last-header-update-date {
        if-feature fibrechannel:fibrechannel_chassis_platform;
        type fru:fru-date-type;
        config false;
        description
          "
          The date since the last FRU header was updated.
          ";
      }
      leaf header-version {
        if-feature fibrechannel:fibrechannel_chassis_platform;
        type uint16 {
         range "0..max";
        }
        config false;
        description
          "
          The FRU header version number.
          ";
      }
      uses fru-time-detail-group;
      uses fru-part-serial-number-group;
      uses fru-vendor-detail-group;
    }
    list fan {
      key "unit-number";
      config false; 
      description
        "
        The details about the fan units.
        ";

      leaf unit-number {
        type uint16 {
          range "1..16"; 
        }
        description
          "
          The physical slot number in the chassis where the fan is located.
          ";
      }
      leaf power-consumption {
         when "../operational-state != 'absent'";
         type fru:power-detail-type;
         units "watts";
         description
           "
           The maximum power consumption allocated for the fan.
           ";
      } 
      leaf operational-state {
        type string {
           length "2..60";
           pattern "faulty|ok|below minimum|above maximum|absent|" +
                   "unknown|not ok";
        }
        description
          "
          The current operational state of the Fan.
          The state 'not ok' displays when the unit is faulty for
          an unknown reason.
          ";
      }
      leaf speed {
        when "../operational-state = 'ok'";
        type uint32 {
           range "1..100000";
        }
        units "RPM";
        description
          "
          The fan speed.
          ";
      }
      leaf airflow-direction {
        when "../operational-state != 'absent'";
        type air-flow-direction-type;
        description
          "
          The air flow direction of the fan blowers.
          ";
      }
      uses fru-time-detail-group {
        when "../operational-state != 'absent'";
      }
      uses fru-part-serial-number-group {
        when "../operational-state != 'absent'";
      }
      leaf manufacture-date {
        type fru:fru-date-type;
        config false;
        description
          "
          The FRU manufacture date.
          ";
      }
      leaf  last-header-update-date {
        if-feature fibrechannel:fibrechannel_chassis_platform;
        type fru:fru-date-type;
        config false;
        description
          "
          The date since the last FRU header was updated.
          ";
      }
      leaf header-version {
        when "../time-alive != '0' and " +
             "../../sensor/state != 'absent'";
        type uint16 {
         range "0..max";
        }
        config false;
        description
          "
          The FRU header version number.
          ";
      }
      uses fru-vendor-detail-group;
    }
    list power-supply {
      key "unit-number";
      config false;
      description
        "
        The details about the power supply units.
        ";

      leaf unit-number {
        type uint16 {
           range "1..16";
        }
        description
          "
          The physical slot number of the chassis where the power supply 
          is located.
          ";
      }
      leaf power-production {
         type uint32 {
           range "0..10000";
         }
         units "watts";
         description
           "
           The maximum power production for the power supply.
           ";
      }
      leaf input-voltage {
        type decimal64 {
          fraction-digits 2;
          range "-1..900.99";
        }
        units "volt";
        description
          "
          The input voltage of the power supply unit.
          Value -1 indicates 'Not Available'.
          ";
      }
      leaf airflow-direction {
        type air-flow-direction-type;
        description
          "
          The airflow direction of the power supply fans.
          ";
      }
      leaf power-source {
        type string {
          length "2..32";
          pattern "AC|DC|HVAC|HVDC|not available";
        }
        description
          "
          The power supply input voltage type.

          HVDC : high-voltage direct current
          HVAC : high-voltage alternating current
          ";
      }
      leaf operational-state {
        type string {
          length "2..30";
          pattern "absent|ok|faulty|predicting failure|" +
                  "unknown, try reseating unit";
        }
        description
          "
          The operational state of the power supply unit.
          ";
      }
      leaf temperature {
        when "../temperature-sensor-supported = true";
        type decimal64 {                  
          fraction-digits 2;
          range "0..300.00";
        }
        units "Centigrade";
        description
          "
          The temperature of the power supply sensor.
          ";
      }
      leaf power-usage {
         type fru:power-detail-type;
         units "watts";
         description
           "
           The real-time power consumed by the FRU.
           ";
      }
      leaf temperature-sensor-supported {
         type boolean;
         description
           "
           Indicates whether the power supply sensor supports
           temperature monitoring.

           false : Temperature monitoring is not supported.
           true  : Temperature monitoring is supported.
           ";
      }
      leaf manufacture-date {
        type fru:fru-date-type;
        config false;
        description
          "
          The FRU manufacture date.
          ";
      }
      leaf  last-header-update-date {
        if-feature fibrechannel:fibrechannel_chassis_platform;
        type fru:fru-date-type;
        config false;
        description
          "
          The date since the last FRU header was updated.
          ";
      }
      leaf header-version {
        when "../time-alive != '0' and " +
             "../../sensor/state != 'absent'";
        type uint16 {
         range "0..max";
        }
        config false;
        description
          "
          The FRU header version number.
          ";
      }
      uses fru-time-detail-group;
      uses fru-part-serial-number-group;
      uses fru-vendor-detail-group;
    }
    list history-log {
      config false;
      description
        "
        The entire history log records of all the FRU's.
        ";
      leaf fru-type {
        type fru:fru-type;
        description
          "
          The type of the fru.
          ";
      }
      leaf position {
        type uint16 {
          range "1..12";
        }
        description
          "
          The physical location where the fru is located.
          For fan and powersupply it is unit number.
          For slot it is slot number.
          ";
      }
      leaf state {
        type fru:state-type;
        description
          "
          The state of the fru.
          ";
      }
      leaf time-stamp {
        type yang:date-and-time;
        description
          "
          Timestamp of the event generated.
          ";
      }
      uses fru-part-serial-number-group;
    }
    list sensor {
      key "id";
      config false;
      description
        "
        The details about sensors.
        ";

      leaf id {
        type uint16 {
         range "1..max";
        }
        description
          "
          The number of the sensor id in the chassis.
          ";
      }
      leaf slot-number {
        type uint16 {
         range "0..12";
        }
        description
          "
          The number of the physical slot in the chassis in which the
          blade is inserted.
          ";
      }
      leaf index {
        type uint16 {
          range "0..max";
        }
        description
          "
          The sensor index in the specific fru.
          ";
      }
      leaf state {
        type fru:operational-state-type;
        description
          "
          The current operational state of the sensor.
          ";
      }
      leaf category {
        type fru:sensor-category;
        description
          "
          The type of the sensor.
          ";
      }
      leaf temperature {
        type uint16 {
          range "0..max";
        }
        units "centigrade";
        description
          "
          The temperature of the fru sensor.
          Value '0' indicates 'Not Available'.
          ";
      }
    }
    list wwn {
      key "unit-number";
      config false;
      description
        "
        The details about the wwn card units.
        ";

      leaf unit-number {
        type uint16 {
           range "1..16";
        }
        description
          "
          The physical slot number of the chassis where the wwn card
          is located.
          ";
      }
      leaf airflow-direction {
        type air-flow-direction-type;
        description
          "
          The system air flow direction.
          ";
      }
      leaf power-usage {
         type fru:power-detail-type;
         units "watts";
         description
           "
           The real-time power consumed by the FRU.
           This parameter is applicable only for chassis.
           ";
      }
      leaf generation-number {
         if-feature fibrechannel:fibrechannel_chassis_platform;
         type uint16 {
           range "6..max";
         }
         description
           "
           The wwn card generation number.
           ";
      }
      leaf manufacture-date {
        type fru:fru-date-type;
        config false;
        description
          "
          The FRU manufacture date.
          ";
      }
      leaf  last-header-update-date {
        type fru:fru-date-type;
        config false;
        description
          "
          The date since the last FRU header was updated.
          ";
      }
      leaf header-version {
        type uint16 {
         range "0..max";
        }
        config false;
        description
          "
          The FRU header version number.
          ";
      }
      leaf time-alive-in-hours {
         type fru:time-detail-type-in-hours;
         units "hours";
         config false;
         description
           "
           The time elapsed in hours since
           the FRU has been powered on.
           ";
      }
      leaf time-awake-in-hours {
         type fru:time-detail-type-in-hours;
         units "hours";
         config false;
         description
           "
           The time elapsed in hours since the FRU
           was manufactured.
           ";
      }
      uses fru-part-serial-number-group;
      uses fru-time-detail-group {
          status obsolete;
          description
            "
            obsolete:
            fru-time-detail-group expresses 'time-alive' and
            'time-awake' in days which is not used for WWN
            cards anymore.
            Please use 'time-alive-in-hours' and
            'time-awake-in-hours' instead.
            ";
      }
      uses fru-vendor-detail-group;
    }
  }
}
