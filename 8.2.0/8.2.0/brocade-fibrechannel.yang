module brocade-fibrechannel {
  namespace "urn:brocade.com:mgmt:brocade-fibrechannel";
  prefix fc;

  import fibrechannel-yang-types {
    prefix fibrechannel;
  }
  import ietf-yang-types {
    prefix yang;
  }

  organization
    "Brocade Communication Systems, Inc.";
  contact
    "Address :  120 Holger Way
                     San Jose, CA 95134
                     U.S.A
     Phone    :  +1-408-333-8000
     E-mail   :  support@brocade.com
     Website  :  www.brocade.com";
  description
    "This module defines the YANG module 'fibrechannel', which augments the
     'interface' and 'interface-state' lists defined in the
     'ietf-interfaces' module [RFC7223] with Fibre Channel data nodes, and
     also adds Fibre Channel state data. ** needs to remove reference to 7223
     
     Copyright (c) 2017 by Brocade Communications Systems, Inc.
     All rights reserved.";

  revision 2017-11-09 {
    description
      "Initial release.";
    reference "None";
  }

  typedef port-type-type {
    type uint16 {
      range "0|7|10|11|15|16|17|19|20|21|22|23|25|26|32768";
    }
    description
      "Fibre Channel Port Types:
         0 - Unknown
         7 - E Port
        10 - G Port
        11 - U Port
        15 - F Port
        16 - L Port
        17 - FCoE Port
        19 - EX Port
        20 - D Port
        21 - SIM Port
        22 - AF Port
        23 - AE Port
        25 - VE Port
        26 - Ethernet Flex Port
        32768 - LB Port";
  }

  typedef speed-type {
    type uint64 {
      range "0|1000000000|2000000000|4000000000|8000000000|10000000000|16000000000|32000000000";
    }
    description
      "The current bandwidth of the Port.
           0 - Auto negotiated.
           1000000000 - 1 GFC
           2000000000 - 2 GFC
           4000000000 - 4 GFC
           8000000000 - 8 GFC
          10000000000 - 10 GFC
          16000000000 - 16 GFC
          32000000000 - 32 GFC";
  }

  container brocade-interface {
    description
      "Contains all fibre channel interface related configuration, operational state, and statistics.";
    list fibrechannel {
      key "name";
      description
        "The list of interfaces on the device.
         
         System-controlled interfaces created by the system are
         always present in this list, whether they are configured or not.";
      leaf name {
        type string {
          /* pattern with 12 slots and 1024 ports seperated by a slash */
          pattern "([1-9]|1[0-9])/(10[0-2][0-9]|[1-9][1-9][0-9]|[1-9][1-9]|[1-9])";
        }
        description
          "The name of the interface. The slot and port number of the port (slot/port).";
      }
      leaf wwn {
        type fibrechannel:wwn-type;
        config false;
        description
          "The port World Wide Name (WWN).";
      }
      leaf operational-status {
        type uint32 {
          range "0|2|3|5";
        }
        config false;
        description
          "The current operational status of the port. The possible values are:
             0 - Undefined
             2 - Online/Testing
             3 - Offline
             5 - Faulty";
      }
      leaf enabled-state {
        type uint32 {
          range "2|6";
        }
        description
          "The current state of the port: The possible values are:
                   2 - Enable
                   6 - Disable";
      }
      leaf user-friendly-name {
        type string {
          length "0..128";
          pattern "[!-+\\--:<-?A-\\[\\]-~]{0,128}";
        }
        description
          "Allows a user friendly name to be assigned to the port.
                     
           A value from 1 to 128 alphanumeric characters. This must not contain special (high-ASCII)
           characters, and is not case-sensitive.
           
           When a port name is not configured, a default name is assigned.
              The format of the default name is as follows:
                 - On standalone platforms, the default port name displays as portportnumber, for example, 'port10'.
                 - On enterprise-class platforms, the default port name displays as slotslotnumber portportnumber, for example,
                    'slot1 port5'.
           
           Provide a null string to replace the existing name with the 
           default.";
      }
      leaf speed {
        type speed-type;
        description
          "The fibre channel interface may operate at various speeds,
              so this leaf allows the interface to be forced to operate at a
              particular speed.
            
              Without any explicit speed set (e.g auto-negotiated set), the
              fibre channel interfaces run at the maximum speed that they 
              are capable of operating at understanding it must negotiate 
              the speed with its neighbor.
           
              Zero is only returned when auto-negotiate is set and the port 
              has not yet negotiated the speed with the other end (e.g. port
              is offline or is syncing). Otherwise the negotiated speed or the
              fixed speed is returned. 
           
              To determine whether the speed was auto-negotiated or fixed, 
              see the auto-negotiate leaf.";
      }
      leaf auto-negotiate {
        type uint8 {
          range "0..1";
        }
        config false;
        description
          "Indicates port speed is auto-negotiated.
             0 - Port speed fixed
             1 - Auto-negotiated";
      }
      leaf g-port-locked {
        type uint8 {
          range "0..1";
        }
        description
          "Designates a port as a G_Port. After successful execution, the switch
           attempts to initialize the specified port as an F_Port only, and does not attempt loop initialization (FL_Port) on the
           port. A port designated as a G_Port can become an E_Port. This configuration can be cleared but not set on
           VE/VEX_Ports. Changes made by this command are persistent across switch reboots or power cycles.
           
           0 - Unlocked to remove the G_Port designation from the port
           1 - Locked to designate the port as a G_Port";
      }
      leaf e-port-disable {
        type uint8 {
          range "0..1";
        }
        description
          "Enables or disables E_Port capability on a port or to lock down a port as an E_Port. E_Port
           capability is enabled by default. When an interswitch link (ISL) is connected to a port and the port's E_Port
           capability is disabled, the ISL is segmented, and all traffic between the switches stops. Fabric management data,
           such as zoning information, can no longer be exchanged through this port.
           
           0 - Enables the ports as E_Ports. This is the default port state.
           1 - Disables E_Port capability for the specified ports.";
      }
      leaf d-port-enable {
        type uint8 {
          range "0..1";
        }
        description
          "Indicates whether this port is configured as a D Port.
                     
           0 - Disabled
           1 - Enabled";
      }
      leaf persistent-disable {
        type uint8 {
          range "0..1";
        }
        description
          "Status of the persistent-disable feature of the port:
                     
           0 - Persistent-disable is not active
           1 - Persistent-disable is active";
      }
      container neighbor {
        config false;
        description
          "A list of WWN's ";
        leaf-list wwn {
          type fibrechannel:wwn-type;
          description
            "The Fibre Channel WWN of the neighbor port.";
        }
      }
      leaf fcid {
        type fibrechannel:fcid-type;
        config false;
        description
          "The Fibre Channel ID (FCID) of the port.";
      }
      leaf port-type {
        type port-type-type;
        config false;
        description
          "The specific port type currently enabled for the port. If the 
           port is logged in, this will be the negotiated port type, otherwise 
           the configured port type will be reported.";
      }
      leaf qos-enabled {
        type uint8 {
          range "0..1";
        }
        description
          "Indicates whether QoS is enabled on the port.
                     
           0 - Disabled
           1 - Enabled";
      }
      leaf compression-configured {
        type uint8 {
          range "0..1";
        }
        description
          "Enables or disables the compression configuration on the port, and saves the change in configuration persistently.
           Configuring a port for compression is disruptive. You must disable the port before you can enable compression on
           the port. This command fails on an enabled port. The values are:
           
             0 - Disables the compression configuration on the specified port.
             1 - Enables the compression configuration on the specified port.
             
           The number of configurable ports is on a per-ASIC basis.";
      }
      leaf compression-active {
        type uint8 {
          range "0..1";
        }
        config false;
        description
          "Indicates the port's runtime compression status:
                     
             0 - Indicates that the port is enabled for compression but offline, or not enabled for compression
             1 - Indicates that the port is online and enabled for compression";
      }
      leaf encryption-active {
        type uint8 {
          range "0..1";
        }
        config false;
        description
          "Encryption status for the interface: // more description
             0 - Disabled
             1 - Enabled";
      }
      leaf target-driven-zoning-enable {
        type uint8 {
          range "0..1";
        }
        description
          "Enables or disables the Target Driven Zoning configuration 
           on the port and saves the configuration persistently. 
           Target Driven Zoning can be configured on E Ports, F Ports, and
           L Ports that are online or offline and it does not toggle the port 
           to apply the configuration. After Target Driven Zoning is configured 
           on the port, it allows the connected target device to configure 
           Target Driven Peer Zones to be enabled and committed.
           
           0 - Disabled
           1 - Enabled";
      }
    }
    list fibrechannel-statistics {
      key "name";
      description
        "The statistics for the interfaces on the device.
         
         System-controlled interfaces created by the system are
         always present in this list, whether they are configured or
         not.";
      leaf name {
        type string {
          /* pattern with 12 slots and 1024 ports seperated by a slash */
          pattern "(([1-9]|1[0-9])/([1][0-9][0-9][0-9]|[1-9][1-9][0-9]|[1-9][1-9]|[1-9]))";
        }
        description
          "The name of the interface. 
           
           The slot and port number of the port (slot/port).";
      }
      leaf sampling-interval {
        type uint16 {
          range "1..max";
        }
        units "seconds";
        config false;
        description
          "Sampling interval in seconds.";
      }
      leaf time-generated {
        type fibrechannel:time-generated-type;
        config false;
        description
          "The time at which the statistics were queried.";
      }
      leaf reset-statistics {
        type uint8 {
          range "0..1";
        }
        description
          "To reset statistical counters, reset-statistics should be set to 1. Zero is always returned during read operations.";
      }
      leaf in-octets {
        type yang:zero-based-counter64;
        config false;
        description
          "The total number of octets received on the interface, including framing characters.";
      }
      leaf out-octets {
        type yang:zero-based-counter64;
        config false;
        description
          "The total number of octets transmitted out of the interface, including framing characters.";
      }
      leaf in-multicast-pkts {
        type yang:zero-based-counter64;
        config false;
        description
          "The number of packets, delivered by this sub-layer to a
           higher (sub-)layer, that were addressed to a multicast
           address at this sub-layer.  For a MAC-layer protocol,
           this includes both Group and Functional addresses.";
      }
      leaf out-multicast-pkts {
        type yang:zero-based-counter64;
        config false;
        description
          "The total number of packets that higher-level protocols
           requested be transmitted, and that were addressed to a
           multicast address at this sub-layer, including those
           that were discarded or not sent.  For a MAC-layer
           protocol, this includes both Group and Functional
           addresses.";
      }
      leaf in-link-resets {
        type yang:zero-based-counter64;
        config false;
        description
          "The number of link resets received.";
      }
      leaf out-link-resets {
        type yang:zero-based-counter64;
        config false;
        description
          "The total number of Link resets transmitted.";
      }
      leaf in-offline-sequences {
        type yang:zero-based-counter64;
        config false;
        description
          "The total number of offline sequences received.";
      }
      leaf out-offline-sequences {
        type yang:zero-based-counter64;
        config false;
        description
          "The total number of offline sequences transmitted.";
      }
      leaf invalid-ordered-sets {
        type yang:zero-based-counter64;
        config false;
        description
          "The total number of invalid ordered sets received.";
      }
      leaf frames-too-long {
        type yang:zero-based-counter64;
        config false;
        description
          "The number of frames received that were longer than 2140 
           octets. The value of 2140 is calculated based on an 
           assumption of 24 header bytes plus 4 CRC bytes and 2112 
           bytes of payload.";
      }
      leaf truncated-frames {
        type yang:zero-based-counter64;
        config false;
        description
          "The total number of truncated frames received.";
      }
      leaf address-errors {
        type yang:zero-based-counter64;
        config false;
        description
          "Count of frames received with unknown addressing. An 
           example is an unknown SID or DID. The SID or DID is not 
           known to the routing algorithm.";
      }
      leaf delimiter-errors {
        type yang:zero-based-counter64;
        config false;
        description
          "Count of invalid frame delimiters that are received at 
           this port. An example is a frame with a class 2 start 
           and a class 3 at the end.";
      }
      leaf encoding-disparity-errors {
        type yang:zero-based-counter64;
        config false;
        description
          "The total number of disparity errors received at this port.";
      }
      leaf too-many-rdys {
        type yang:zero-based-counter64;
        config false;
        description
          "The number of times RDYs exceed frames received.";
      }
      leaf in-crc-errors {
        type yang:zero-based-counter64;
        config false;
        description
          "The number of CRC errors for all frames received.";
      }
      leaf crc-errors {
        type yang:zero-based-counter64;
        config false;
        description
          "Number of times that the CRC in a frame does not match 
           the CRC that is computed by the receiver. This count is
           part of the Link Error Status Block (LESB).";
      }
      leaf bad-eofs-received {
        type yang:zero-based-counter64;
        config false;
        description
          "The number of bad EOF frames received.";
      }
      leaf encoding-errors-outside-frame {
        type yang:zero-based-counter64;
        config false;
        description
          "The number of encoding error or disparity error outside frames received.";
      }
      leaf multicast-timeouts {
        type yang:zero-based-counter64;
        config false;
        description
          "The number of multicast frames that have timed out.";
      }
      leaf in-lcs {
        type yang:zero-based-counter64;
        config false;
        description
          "The number of link control frames received.";
      }
      leaf in-frame-rate {
        type yang:zero-based-counter64;
        config false;
        description
          "The instantaneous receive frame rate.";
      }
      leaf out-frame-rate {
        type yang:zero-based-counter64;
        config false;
        description
          "The instantaneous transmit frame rate.";
      }
      leaf in-max-frame-rate {
        type yang:zero-based-counter64;
        config false;
        description
          "The maximum frame receive rate since last reset.";
      }
      leaf out-max-frame-rate {
        type yang:zero-based-counter64;
        config false;
        description
          "The maximum frame transmit rate since last reset.";
      }
      leaf in-rate {
        type yang:zero-based-counter64;
        config false;
        description
          "The instantaneous byte receive rate.";
      }
      leaf out-rate {
        type yang:zero-based-counter64;
        config false;
        description
          "The instantaneous byte transmit rate.";
      }
      leaf in-peak-rate {
        type yang:zero-based-counter64;
        config false;
        description
          "The peak byte receive rate.";
      }
      leaf out-peak-rate {
        type yang:zero-based-counter64;
        config false;
        description
          "The peak byte transmit rate.";
      }
      leaf in-frames {
        type yang:zero-based-counter64;
        config false;
        description
          "Number of frames received.";
      }
      leaf out-frames {
        type yang:zero-based-counter64;
        config false;
        description
          "Number of frames transmitted.";
      }
      leaf bb-credit-zero {
        type yang:zero-based-counter64;
        config false;
        description
          "The number of transitions in and out of BBcredit zero state";
      }
      leaf input-buffer-full {
        type yang:zero-based-counter64;
        config false;
        description
          "The number of transitions in and out of Input Buffer Full state.";
      }
      leaf f-busy-frames {
        type yang:zero-based-counter64;
        config false;
        description
          "The number of F_BSY frames generated.";
      }
      leaf p-busy-frames {
        type yang:zero-based-counter64;
        config false;
        description
          "Number of P_BSY frames generated.";
      }
      leaf f-rjt-frames {
        type yang:zero-based-counter64;
        config false;
        description
          "Number of F_RJT frames generated.";
      }
      leaf p-rjt-frames {
        type yang:zero-based-counter64;
        config false;
        description
          "Number of P_RJT frames generated.";
      }
      leaf class-1-frames {
        type yang:zero-based-counter64;
        config false;
        description
          "Number of Class 1 frames received";
      }
      leaf class-2-frames {
        type yang:zero-based-counter64;
        config false;
        description
          "Number of Class 2 frames received";
      }
      leaf class-3-frames {
        type yang:zero-based-counter64;
        config false;
        description
          "Number of Class 3 frames received";
      }
      leaf class-3-discards {
        type yang:zero-based-counter64;
        config false;
        description
          "Number of Class 3 frames discarded by the port.";
      }
      leaf link-failures {
        type yang:zero-based-counter64;
        config false;
        description
          "Number of link failures.";
      }
      leaf invalid-transmission-words {
        type yang:zero-based-counter64;
        config false;
        description
          "Number of invalid transmission words received.";
      }
      leaf primitive-sequence-protocol-error {
        type yang:zero-based-counter64;
        config false;
        description
          "Number of primitive sequence protocol errors detected at this port.";
      }
      leaf loss-of-signal {
        type yang:zero-based-counter64;
        config false;
        description
          "Number of instances of signal loss detected at this port.";
      }
      leaf loss-of-sync {
        type yang:zero-based-counter64;
        config false;
        description
          "Number of instances of synchronization loss detected at this port.";
      }
      leaf class3-in-discards {
        type yang:zero-based-counter64;
        config false;
        description
          "Number of C3 receive frames discarded due to timeout";
      }
      leaf class3-out-discards {
        type yang:zero-based-counter64;
        config false;
        description
          "Number of C3 transmit frames discarded due to timeout";
      }
      leaf pcs-block-errors {
        type yang:zero-based-counter64;
        config false;
        description
          "The number of Physical Coding Sublayer (PCS) block errors. This counter records encoding
                 violations on 10 Gbps or 16 Gbps ports.";
      }
    }
  }
}
