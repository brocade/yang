module brocade-zone {
  namespace "urn:brocade.com:mgmt:brocade-zone";
  prefix brocade-zone;

  import fibrechannel-yang-types {
    prefix brocade;
  }

  organization
    "Brocade Communication Systems, Inc.";
  contact
    "Address :  120 Holger Way
                     San Jose, CA 95134
                     U.S.A
     Phone    :  +1-408-333-8000
     E-mail   :  support@brocade.com
     Website  :  www.brocade.com";
  description
    "The module for managing Fibre Channel zoning.
     
     Copyright (c) 2017 by Brocade Communications Systems, Inc.
     All rights reserved.";

  revision 2017-11-01 {
    description
      "Initial release.";
    reference "None";
  }

  typedef zone-type-type {
    type uint8 {
      range "0|1|2";
    }
    description
      "The zone type. The values are:
           default: 0
           user: 1
           target:2";
  }

  typedef zoning-name-type {
    type string {
      length "1..64";
      pattern "([0-9a-zA-Z_\\-^$]{1,64})";
    }
    description
      "Fibre channel zoning names can consist of 
         alphanumeric, '$', '^', '-', and '_' characters of max 
         length of 64 characters and are case sensitive. The 
         pattern checking verifies that the specified name 
         consists or alphanumeric characters and underline 
         characters only.";
  }

  typedef domain-index-type {
    type string {
      pattern
        "([1-9]|[1-9][0-9]|1[0-9][0-9]|2[0123][0-9]),(([0-9])|
            ([1-9][0-9])|([1-9][0-9][0-9])|([1-9][0-9][0-9][0-9])|
            ([1-5][0-9][0-9][0-9][0-9])|(6[0-4][0-9][0-9][0-9])|
            (65[0-4][0-9][0-9])|
            (655[0-2][0-9])|(6553[0-5]))";
    }
    description
      "Domain/index zone members appear as d,i. Domain is between 1 
         and 239 and port is between 0 and 65535.";
  }

  typedef zone-member-type {
    type union {
      type zoning-name-type;
      type brocade:wwn-type;
      type domain-index-type;
    }
    description
      "The zone member typedef defines as a union the three different 
         zone member types (WWN, domain,index, or zone alias).";
  }  

  container zoning {
    description
      "The zoning defined configuration and the effective configuration. ";
    container defined-configuration {
      description
        "Contains the defined zoning configuration.";
      list cfg {
        key "cfg-name";
        description
          "The name of the zone configuration.";
        leaf cfg-name {
          type zoning-name-type;
          description
            "The zone configuration name.";
        }
        container member-zone {
          description
            "The list of zone members in the configuration.";
          leaf-list zone-name {
            type zoning-name-type;
            min-elements 1;
            description
              "The zone name.";
          }
        }
      }
      list zone {
        key "zone-name";
        description
          "List of the members in the zone. The members can only be identified 
              as a WWN, domain,index, or a zone alias.";
        leaf zone-name {
          type zoning-name-type;
          description
            "The zone name.";
        }
        leaf zone-type {
          type zone-type-type;
          description
            "The zone type.
            
                 Not that target zone types cannot be created or modified 
                 (only deleted).";
        }
        container member-entry {
          description
            "The zone member.";
          leaf-list entry-name {
            type zone-member-type;
            min-elements 1;
            description
              "List of the members in the zone. The members can only be 
                   identified as a WWN, domain,index, or zone alias.";
          }
          leaf-list principal-entry-name {
            when "../..zone-type = 1 or ../../zone-type = 2";
            type zone-member-type;
            min-elements 1;
            description
              "List of the principal members in the peer zone. The members can 
                   only be identified as a WWN, domain,index, or zone alias.";
          }
        }
      }
      list alias {
        key "alias-name";
        description
          "The list of zone aliases.";
        leaf alias-name {
          type zoning-name-type;
          description
            "The zone alias name.";
        }
        container member-entry {
          description
            "The alias member.";
          leaf-list alias-entry-name {
            type union {
              type brocade:wwn-type;
              type domain-index-type;
            }
            min-elements 1;
            description
              "The zone alias. The members are either a port WWN or a
                   domain,index.";
          }
        }
      }
    }
    container effective-configuration {
      description
        "Contains the effective zoning configuration.";
      leaf cfg-name {
        type zoning-name-type;
        description
          "The name of the effective configuration. If written, it is
           the name of a defined configuration that is to be enabled.";
      }
      leaf checksum {
        type string {
          length "32";
          pattern "[0-9a-fA-F]{32}";
        }
        must "../cfg-name or (../cfg-action = 1) or (../cfg-action = 2)";
        description
          "The checksum of the configuration database. The checksum is a   
              MD5 (Message-Digest algorithm 5) calculation
              (128-bit cryptographic hash) used to verify data integrity. This  
              resource is used by the client to verify the zone database has  
              not changed since the configuration was read. It should be read 
              as part of the initial query before modifications are desired. 
              It must be written when the changes are saved and the changes 
              will be accepted if the checksum agrees and rejected if it does 
              not.";
      }
      leaf cfg-action {
        type uint8 {
          range "0..4";
        }
        description
          "The action to be done to the pending zoning configuration changes.
           The possible values are:
           Read is not applicable: 0
                 Save the pending changes: 1
                 Disables the effective configuration: 2.
                 Clears the entire zone database: 3.
                 Clear any pending changes: 4";
      }
      leaf default-zone-access {
        type uint8 {
          range "0..1";
        }
        description
          "Enable or disable default zone access. The default zoning mode 
              controls device access if zoning is not implemented or if there is
              no enabled zone configuration. Currently, default zoning has 
              two access modes. They are as follows:
           
               0 - Devices in the fabric cannot access any other device in the
                     fabric (all access).
               1 - All devices within the fabric can communicate with all other 
                     devices (no access).";
      }
      leaf db-max {
        type uint32 {
          range "0..2084640";
        }
        units "bytes";
        config false;
        description
          "The Zone DB maximum size. The Zone DB maximum size upper 
              limit for the Zone defined configuration, determined by the 
              amount of nonvolatile memory available for storing the defined
              configuration. The Zone DB maximum size is further reduced due 
              to a message header that is propagated with the zone  
              configuration to all switches in the fabric.
           
              The maximum supported zone database size is 2 MB for chassis
              based switches and 1 MB for other switches.";
      }
      leaf db-avail {
        type uint32 {
          range "0..2084640";
        }
        units "bytes";
        config false;
        description
          "Amount of free space in bytes available in the zone database.";
      }
      leaf db-committed {
        type uint32 {
          range "0..2084640";
        }
        units "bytes";
        config false;
        description
          "The size in bytes of the defined configuration currently stored  
              in nonvolatile memory. If the context is for a virtual fabric,   
              then this resource is the size of the defined configuration for   
              the logical switch.";
      }
      leaf db-transaction {
        type uint32 {
          range "0..2084640";
        }
        units "bytes";
        config false;
        description
          "DB transaction Size is the size in memory of the uncommitted 
              defined configuration (the amount of memory required to commit 
              the current transaction). DB transaction size will be nonzero if  
              the defined configuration is being modified by RESTConf, Telnet, 
              API, and so forth; otherwise it is 0.";
      }
      leaf transaction-token {
        type uint32 {
          range "0..4294967280";
        }
        config false;
        description
          "The token for the current zoning transaction. Will be zero if there 
              is no outstanding zoning transaction.";
      }
      leaf db-chassis-wide-committed {
        type uint32 {
          range "0..2092741";
        }
        units "bytes";
        config false;
        description
          "The size in bytes used for the zone database across all the logical
              switches in the chassis if virtual fabrics are in use. 
           
              Otherwise, this is the size of the zone database for the switch.
              Note that the db-committed will be smaller than this resource 
              due to some storage used for overhead.";
      }
      list enabled-zone {
        key "zone-name";
        config false;
        description
          "The enabled zones.";
        leaf zone-name {
          type zoning-name-type;
          description
            "The name of the zone.";
        }
        leaf zone-type {
          type zone-type-type;
          description
            "The zone type.";
        }
        container member-entry {
          description
            "The zone members. ";
          leaf-list entry-name {
            type union {
              type zoning-name-type;
              type brocade:wwn-type;
            }
            description
              "List of the members in the zone. The members can only be 
                   identified as either a WWN or domain,index. Zone aliases are
                   expanded when the configuration is enabled and are not 
                   included in the effective configuration.";
          }
          leaf-list principal-entry-name {
            when "../..zone-type = 1 or ../../zone-type = 2";
            type union {
              type brocade:wwn-type;
              type domain-index-type;
            }
            description
              "If the zone is a peer zone, this property contains the list of
                   principals in the zone. The members can only be identified  
                   as either a WWN or domain,index. Zone aliases are expanded
                   when the configuration is enabled and are not included in
                   the effective configuration.";
          }
        }
      }
    }
  }
}
