module brocade-fibrechannel-switch {
  namespace "urn:brocade.com:mgmt:brocade-fabric";
  prefix switch;

  import ietf-yang-types {
    prefix yang;
  }
  import ietf-inet-types {
    prefix inet;
  }
  import fibrechannel-yang-types {
    prefix fibrechannel;
  }

  organization
    "Brocade Communication Systems, Inc.";
  contact
    "Address :  120 Holger Way
                     San Jose, CA 95134
                     U.S.A
     Phone    :  +1-408-333-8000
     E-mail   :  support@brocade.com
     Website  :  www.brocade.com";
  description
    "This module defines the YANG module 'switch', which provides
     a detailed view of all of the switches in the fabric that are operational.
          
     Copyright (c) 2017 by Brocade Communications Systems, Inc.
     All rights reserved.";

  revision 2017-10-16 {
    description
      "Initial release.";
    reference "None";
  }

  container switch {
    description
      "Switch state paramaters. Currently, requests are made using QUERY 
         specifiying the vf-id of the specific fabric which will provide the  
         switch state parameters.";
    list fibrechannel-switch {
      key "name";
      description
        "Switch state paramaters. Currently, requests are made using QUERY
           specifiying the vf-id of the specific fabric which will provide the 
           switch state parameters.";
      leaf name {
        type fibrechannel:wwn-type;
        description
          "";
      }
      leaf domain-id {
        type fibrechannel:domain-id-type;
        description
          "The highest level in a three-level addressing
                 hierarchy used in the Fibre Channel address identifier. A
                 domain typically is associated with a single Fibre Channel
                 switch.";
      }
      leaf user-friendly-name {
        type string {
          length "30";
          pattern "([0-9a-fA-F][0-9a-zA-Z-._]{2,30})|([0-9][0-9a-zA-Z-._]{2,30})";
        }
        description
          "An ascii name assigned to the switch by the administrator.";
      }
      leaf fcid {
        type fibrechannel:fcid-type;
        config false;
        description
          "The destination id (D_ID) of the switch.";
      }
      leaf vf-id {
        type int16 {
          range "-1|1..128";
        }
        config false;
        description
          "This is the virtual fabric identification (VFID) of the logical switch.
           -1 indicates that VF feature is unsupported or disabled";
      }
      leaf principal {
        type uint8 {
          range "0..1";
        }
        config false;
        description
          "Indicates if this switch is the fabric principal switch. The possible
              values are:
                1 - Switch is principal switch
                0 - Switch is not principal switch";
      }
      leaf enabled-state {
        type uint32 {
          range "0|2|3|7";
        }
        description
          "The current state of the switch. The possible values are:
             Undefined: 0
             Enable: 2
             Disable: 3
             Testing: 7
           
           Note that enabled-state cannot be set to Testing or Undefined. Only Enable and Disable.";
      }
      leaf up-time {
        type yang:timeticks;
        config false;
        description
          "The period of time elapsed since last reboot. This value represents an absolute 
           time interval that the switch has been up and NOT the time measured between 
           the last reboot and midnight, January 1, 1970 UTC.";
      }
      leaf model {
        type string {
          length "5";
        }
        config false;
        description
          "Model name of the switch.";
      }
      leaf firmware-version {
        type string {
          length "256";
        }
        config false;
        description
          "A human readable string identifying the firmware version running
           on the switch.";
      }
      container ip-address {
        leaf-list ip-address {
          type inet:ip-address;
          description
            "List of out-of-band ip addresses assigned to the switches ethernet port.";
        }
        description
          "Container needed by underlying infrastructure.";
      }
      leaf domain-name {
        type string {
          length "0..63";
          pattern "([a-zA-Z]{0,1}[0-9a-zA-Z_]{2,3}[0-9a-zA-Z_]{4,63})";
        }
        description
          "The DNS domain name of the switch.
                     
           The DNS domain name cannot exceed 63 characters in length, with the first character only allowed to be an alpha characters, 
           and the remainder containing alphanumeric characters. 
           The only special character allowed is an underscore (_). which can be in any position except the first character.
                     
           Passing a null string will clear the domain name.";
      }
      leaf fabric-user-friendly-name {
        type string {
          length "128";
        }
        description
          "An ascii name given to the fabric.";
      }
      leaf ag-mode {
        type uint8 {
          range "0|1|3";
        }
        config false;
        description
          "Indicates the Access Gateway (AG) mode capability and enablement
           state. The switch is capable of AG mode support when this value is not zero:
             0 - AG mode is not supported by this device
             1 - AG mode is supported and currently disabled
             3 - AG mode is supported and currently enabled";
      }
    }
  }
}
