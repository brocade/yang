module brocade-fibrechannel {
  namespace "urn:brocade.com:mgmt:brocade-fibrechannel";
  prefix fc;

  import fibrechannel-yang-types {
    prefix fibrechannel;
  }
  import ietf-yang-types {
    prefix yang;
  }

  organization
    "Brocade Communication Systems, Inc.";
  contact
    "
    Address  :  120 Holger Way
                San Jose, CA 95134
                U.S.A
    Phone    :  +1-408-333-8000
    E-mail   :  support@brocade.com
    Website  :  www.brocade.com
    ";
  description
    "
    This module defines the YANG module 'fibrechannel', which augments the
    'interface' and 'interface-state' lists defined in the 'ietf-interfaces'
    module [RFC-7223] with Fibre Channel data nodes, and also adds Fibre Channel
    state data.

    Copyright (c) 2017-2018 by Brocade Communications Systems, Inc.
    All rights reserved.
    ";

  revision 2018-02-14 {
    description
      "
      Fabric OS 8.2.0a
      ----------------
        Deprecated 'fcid' (replaced by 'fcid-hex')
      ";
    reference "None";
  }

  typedef port-type-type {
    type uint16 {
      range "0|7|10|11|15|16|17|19|20|21|22|23|25|26|32768";
    }
    description
      "
      Fibre Channel Port Types:

      0     : Unknown
      7     : E Port
      10    : G Port
      11    : U Port
      15    : F Port
      16    : L Port
      17    : FCoE Port
      19    : EX Port
      20    : D Port
      21    : SIM Port
      22    : AF Port
      23    : AE Port
      25    : VE Port
      26    : Ethernet Flex Port
      32768 : LB Port
      ";
  }

  typedef speed-type {
    type uint64 {
      range "0|1000000000|2000000000|4000000000|8000000000|10000000000|16000000000|32000000000";
    }
    description
      "
      The current bandwidth of the Port.

      0             : Auto negotiated.
      1000000000    : 1 GFC
      2000000000    : 2 GFC
      4000000000    : 4 GFC
      8000000000    : 8 GFC
      10000000000   : 10 GFC
      16000000000   : 16 GFC
      32000000000   : 32 GFC
      ";
  }

  container brocade-interface {
    description
      "
      Contains all fibre channel interface related configuration,
      operational state, and statistics.
      ";
    list fibrechannel {
      key "name";
      description
        "
        The list of interfaces on the device.

        System-controlled interfaces created by the system are
        always present in this list, whether they are configured or not.
        ";
      leaf name {
        type string {
          /* pattern with 12 slots and 1024 ports seperated by a slash */
          pattern "([1-9]|1[0-9])/(10[0-2][0-9]|[1-9][1-9][0-9]|[1-9][1-9]|[1-9])";
        }
        description
          "
          The name of the interface. The slot and port number of the
          port (slot/port).
          ";
      }
      leaf wwn {
        type fibrechannel:wwn-type;
        config false;
        description
          "The port World Wide Name (WWN).";
      }
      leaf operational-status {
        type uint32 {
          range "0|2|3|5";
        }
        config false;
        description
          "
          The current operational status of the port. The possible values are:

          0 : Undefined
          2 : Online/Testing
          3 : Offline
          5 : Faulty
          ";
      }
      leaf enabled-state {
        type uint32 {
          range "2|6";
        }
        description
          "
          The current state of the port - the possible values are:

          2 : Enable
          6 : Disable
          ";
      }
      leaf user-friendly-name {
        type string {
          length "0..128";
          pattern "[!-+\\--:<-?A-\\[\\]-~]{0,128}";
        }
        description
          "
          Allows a user friendly name to be assigned to the port.

          A value from 1 to 128 alphanumeric characters. This must not contain
          special (high-ASCII) characters, and is not case-sensitive.

          When a port name is not configured, a default name is assigned.
          The format of the default name is as follows:

            - On standalone platforms, the default port name displays as
              portportnumber, for example, 'port10'.
            - On enterprise-class platforms, the default port name displays as
              slotslotnumber portportnumber, for example:

                    'slot1 port5'.

          Provide a null string to replace the existing name with the default.
          ";
      }
      leaf speed {
        type speed-type;
        description
          "
          The fibre channel interface may operate at various speeds, so this
          leaf allows the interface to be forced to operate at a particular
          speed.

          Without any explicit speed set (e.g auto-negotiated set), the fibre
          channel interfaces run at the maximum speed that they are capable of
          operating at understanding it must negotiate the speed with its
          neighbor.

          Zero is only returned when auto-negotiate is set and the port has not
          yet negotiated the speed with the other end (e.g. port is offline or
          is syncing). Otherwise the negotiated speed or the fixed speed is
          returned.

          To determine whether the speed was auto-negotiated or fixed, see the
          auto-negotiate leaf.
          ";
      }
      leaf auto-negotiate {
        type uint8 {
          range "0..1";
        }
        config false;
        description
          "
          Indicates port speed is auto-negotiated.

          0 : Port speed fixed
          1 : Auto-negotiated
          ";
      }
      leaf g-port-locked {
        if-feature fibrechannel:fibrechannel_switch_platform;
        type uint8 {
          range "0..1";
        }
        description
          "
          Designates a port as a G_Port. After successful execution, the switch
          attempts to initialize the specified port as an F_Port only, and does
          not attempt loop initialization (FL_Port) on the port. A port
          designated as a G_Port can become an E_Port. This configuration can be
          cleared but not set on VE/VEX_Ports. Changes made by this command are
          persistent across switch reboots or power cycles.

          0 : Unlocked to remove the G_Port designation from the port
          1 : Locked to designate the port as a G_Port
          ";
      }
      leaf e-port-disable {
        if-feature fibrechannel:fibrechannel_switch_platform;
        type uint8 {
          range "0..1";
        }
        description
          "
          Enables or disables E_Port capability on a port or to lock down a port
          as an E_Port. E_Port capability is enabled by default. When an
          inter-switch link (ISL) is connected to a port and the port's E_Port
          capability is disabled, the ISL is segmented, and all traffic between
          the switches stops. Fabric management data, such as zoning
          information, can no longer be exchanged through this port.

          0 : Enables the ports as E_Ports. This is the default port state.
          1 : Disables E_Port capability for the specified ports.
          ";
      }
      leaf n-port-enabled {
        if-feature fibrechannel:access_gateway_platform;
        type uint8 {
          range "0..1";
        }
        description
          "
          Indicates if a port can operate as N-Port. A port can operate as
          n-port only in Access Gateway Mode.

          0 : N-Port disabled
          1 : N-Port enabled
          ";
      }
      leaf d-port-enable {
        type uint8 {
          range "0..1";
        }
        description
          "
          Indicates whether this port is configured as a D Port.

          0 : Disabled
          1 : Enabled
          ";
      }
      leaf persistent-disable {
        type uint8 {
          range "0..1";
        }
        description
          "
          Status of the persistent-disable feature of the port:

          0 : Persistent-disable is not active
          1 : Persistent-disable is active
          ";
      }
      container neighbor {
        config false;
        description
          "A list of WWN's ";
        leaf-list wwn {
          type fibrechannel:wwn-type;
          description
            "The Fibre Channel WWN of the neighbor port.";
        }
      }
      leaf fcid {
        type fibrechannel:fcid-type;
        config false;
        status deprecated;
        description
          "
          The Fibre Channel ID (FCID) of the port. (decimal format)

          Deprecated: Please use 'fcid-hex' leaf instead.
          ";
      }
      leaf fcid-hex {
        type fibrechannel:fcid-hex-string-type;
        config false;
        description
          "The Fibre Channel ID (FCID) of the port. (hexadecimal format)";
      }
      leaf port-type {
        type port-type-type;
        config false;
        description
          "
          The specific port type currently enabled for the port. If the port is
          logged in, this will be the negotiated port type, otherwise the
          configured port type will be reported.
          ";
      }
      leaf qos-enabled {
        type uint8 {
          range "0..1";
        }
        description
          "
          Indicates whether QoS is enabled on the port.

          0 : Disabled
          1 : Enabled
          ";
      }
      leaf compression-configured {
        type uint8 {
          range "0..1";
        }
        description
          "
          Enables or disables the compression configuration on the port, and
          saves the change in configuration persistently. Configuring a port for
          compression is disruptive. You must disable the port before you can
          enable compression on the port. This command fails on an enabled port.
          The values are:

          0 : Disables the compression configuration on the specified port
          1 : Enables the compression configuration on the specified port

          The number of configurable ports is on a per-ASIC basis.
          ";
      }
      leaf compression-active {
        type uint8 {
          range "0..1";
        }
        config false;
        description
          "
          Indicates runtime compression status for the port:

          0 : Indicates that the port is enabled for compression but offline,
              or not enabled for compression
          1 : Indicates that the port is online and enabled for compression
          ";
      }
      leaf encryption-active {
        if-feature fibrechannel:fibrechannel_switch_platform;
        type uint8 {
          range "0..1";
        }
        config false;
        description
          "
          Encryption status for the interface:

          0 : Disabled
          1 : Enabled
          ";
      }
      leaf target-driven-zoning-enable {
        type uint8 {
          range "0..1";
        }
        description
          "
          Enables or disables the Target Driven Zoning configuration on the port
          and saves the configuration persistently. Target Driven Zoning can be
          configured on E Ports, F Ports, and L Ports that are online or offline
          and it does not toggle the port to apply the configuration. After
          Target Driven Zoning is configured on the port, it allows the
          connected target device to configure Target Driven Peer Zones to be
          enabled and committed.

          0 : Disabled
          1 : Enabled
          ";
      }
      leaf sim-port-enabled {
        if-feature fibrechannel:fibrechannel_switch_platform;
        type uint8 {
          range "0..1";
        }
        description
          "
          Configure the port as a SIM port.

          0 : SIM Port is disabled
          1 : SIM Port is enabled on the port
          ";
      }
      leaf mirror-port-enabled {
        type int8 {
          range "-1|0..1";
        }
        description
          "
          Configures the port as a mirror port. The port mirroring feature
          reroutes data frames between two devices to the mirror port.

           0 : Mirror Port is disabled
           1 : Mirror Port is enabled on the port
          -1 : Not Applicable when received as response for GET operation
          ";
      }
      leaf credit-recovery-enabled {
        type int8 {
          range "-1|0..1";
        }
        description
          "
          Configure credit recovery on a port. The credit recovery feature
          enables credits or frames to be recovered. The default credit recovery
          configuration is enabled.

           0 : Credit Recovery is disabled
           1 : Credit Recovery is enabled on the port
          -1 : Not Applicable when received as response for GET operation
          ";
      }
      leaf credit-recovery-active {
        type int8 {
          range "-1|0..1";
        }
        config false;
        description
          "
          This describes if the credit recovery feature is active on the port.
          The credit-recovery will be active only if both the ends supports it.

           0 : Credit Recovery is not active on the port
           1 : Credit Recovery is active on the port
          -1 : Not Applicable when received as response for GET operation
          ";
      }
      leaf fec-active {
        type int8 {
          range "-1|0..1";
        }
        config false;
        description
          "
          This describes if the Forward Error Correction (FEC) feature is active
          on the port. FEC will be active only if both the ends supports it.

           0 : FEC is not active on the port
           1 : FEC is active on the port
          -1 : Not Applicable when received as response for GET operation
          ";
      }
      leaf f-port-buffers {
        type uint8 {
          range "0|8..max";
        }
        description
          "
          Configured the buffer allocation for an F_Port. The minimum buffer
          allocation is the default number of buffers plus 1. The maximum is
          determined by the remaining buffer allocations in the port's port
          group. If no buffers are configured, the value is zero.

          The F_Port buffer feature does not support ports configured as
          EX_Ports, Mirror Ports, Long Distance Ports, L_Ports, QoS Ports,
          Fast Write, and Trunk Areas.
          ";
      }
      leaf e-port-credit {
        type uint8 {
          range "0|5..160";
        }
        description
          "
          Configures the number of credits to be allocated to the specified port.
          The minimum credit allocation is 5 and the maximum can be up to 160
          depending on the platform. If no value is 0.
          ";
      }
      leaf csctl-mode-enabled {
        if-feature fibrechannel:fibrechannel_switch_platform;
        type int8 {
          range "-1|0..1";
        }
        description
          "
          Configure a port to enable Class-Specific Control (CSCTL) mode which
          enables traffic prioritization based on CS_CTL.

           0 : Disables CSCTL mode on the port
           1 : Enables CSCTL mode on the port
          -1 : Not Applicable when received as response for GET operation
          ";
      }
      leaf fault-delay-enabled {
        type uint8 {
          range "0..1";
        }
        default "0";
        description
          "
          Configures the fault delay for a port.

          In the event that the link is noisy after a host power cycle, the
          switch may go into a soft fault state, which means a delay of R_A_TOV.
          Setting the mode value to 1 reduces the fault delay value to 1.2
          seconds. The configuration is stored in nonvolatile memory and is
          persistent across switch reboots and power cycles.

          0 : if the value is R_A_TOV. This is the default
          1 : if the value is 1.2 seconds
          ";
      }
      leaf octet-speed-combo {
        type int8 {
          range "-1|1..3";
        }
        default "1";
        description
          "
          Displays the speed configuration for a port octet. Valid Octet Combo
          values include the following:


           1 : Autonegotiated or fixed port speeds of 32Gbps, 16 Gbps,
               8 Gbps, 4 Gbps, and 2 Gbps

           2 : Autonegotiated or fixed port speeds of 10 Gbps, 8 Gbps,
               4 Gbps, and 2 Gbps

           3 : Autonegotiated or fixed port speeds of 16 Gbps and 10 Gbps
          -1 : Not Applicable when received as response for GET operation

          A port octet can be set to any of the three octet combinations, and
          the ports in the octet can run on any speed supported by its octet
          combination. This applies to both auto-negotiated and fixed speeds.

          The octet combination default is 1.
          ";
      }
      leaf trunk-port-enabled {
        type uint8 {
          range "0..1";
        }
        description
          "
          Enable or disable trunking on a port.

          0 : OFF when trunking is disabled on the port
          1 : ON when port is set for trunking

          Trunking is enabled by default, when a trunking license is present
          on the switch.
          ";
      }
      leaf long-distance {
        if-feature fibrechannel:fibrechannel_switch_platform;
        type uint8 {
          range "0..7";
        }
        config false;
        description
          "
          Specifies the long distance level as one of the following
          (the numerical value representing each distance level is shown
          in parentheses):

          0 : Long-Distance is disabled for this port
          1 : Specifies L0 to configure the port as a regular port
          2 : Specifies L1 (long <= 50km)
          3 : Specifies L2 (super long <= 100km)
          4 : Specifies LE mode to configure an E_Ports distance greater than
              5 km and up to 10 km
          5 : Specifies L0.5 for medium long (<= 25km)
          6 : Specifies LD for automatic long-distance configuration
          7 : Specifies LS mode to configure a static long distance link with a
              fixed buffer allocation greater than 10 km
          ";
      }
      leaf vc-link-init {
        if-feature fibrechannel:fibrechannel_switch_platform;
        type uint8 {
          range "0..1";
        }
        config false;
        description
          "
          VC Link initialization.

          0 : The long distance link initialization option is turned off
          1 : The long distance link initialization option is turned on for long
              distance mode
          ";
      }
      leaf isl-ready-mode-enabled {
        if-feature fibrechannel:fibrechannel_switch_platform;
        type uint8 {
          range "0..1";
        }
        description
          "
          0 : ISL R_RDY mode is disabled on the port
          1 : ISL R_RDY mode is enabled on the port
          ";
      }
      leaf rscn-suppression-enabled {
        if-feature fibrechannel:fibrechannel_switch_platform;
        type uint8 {
          range "0..1";
        }
        description
          "
          Manages Registered State Change Notification (RSCN) suppression on the
          port.

          0 : Disables RSCN suppression on the port. When disabled, device
              changes on the port generate an RSCN to all other end devices that
              are zoned with this one. By default, RSCN suppression is disabled
              on all ports.
          1 : Enables RSCN suppression on the port. When enabled, any device
              changes on the port will not generate an RSCN to any other end
              device.
          ";
      }
      leaf los-tov-mode-enabled {
        type uint8 {
          range "0..2";
        }
        description
          "
          Enables or disables de-bouncing of signal loss for front end ports.
          Use this resource to enable or disable the de-bouncing of loss of
          signal for 100 ms for front end ports.

          0 : Disabled
          1 : Enabled on fixed speed ports
      2 : Enabled for both Fixed speed and Auto-neg port
          ";
      }
      leaf npiv-enabled {
        type uint8 {
          range "0..1";
        }
        default 1;
        description
          "
          Enables NPIV capability on the port

          0 : Disabled
          1 : Enabled
          ";
      }
      leaf npiv-pp-limit {
        type int16 {
          range "-1|1..255";
        }
        default 126;
        description
          "
          Displays the maximum number of allowed logins for the port. Valid
          values are 1 to 255.

           1 - 255 : Maximum number of allowed logins for the port
          -1       : Not Applicable when received as response for GET operation
          ";
      }
      leaf npiv-flogi-logout-enabled {
        type int8 {
          range "-1|0..1";
        }
        config false;
        description
          "
          Configures the base device logout feature.

           0 : The base device log out causes the NPIV devices on the same
               port to log out
           1 : The Base Device Logout feature is enabled and the base device
               can logout without disrupting the NPIV devices on the same port
          -1 : Not Applicable when received as response for GET operation
          ";
      }
      leaf ex-port-enabled {
        if-feature fibrechannel:fibrechannel_switch_platform;
        type uint8 {
          range "0..1";
        }
        description
          "
          Configure a port as an EX port.

          0 : The port is not configured as an EX Port
          1 : The port is configured as an EX Port
          ";
      }
      leaf fec-enabled {
        type int8 {
          range "-1|0..1";
        }
        default "1";
        description
          "
          Configures Forward Error Correction (FEC) on a port.

          FEC provides a mechanism for reducing error rates during data
          transmissions over 16 Gbps Fibre Channel links. When FEC is enabled
          on a port, the sender adds systematically generated error-correcting
          code (ECC) to its data transmission. This mechanism allows the
          receiver to detect and correct errors without needing to get
          additional information from the sender.

            0 : Forward Error Correction (FEC) is disabled
            1 : Forward Error Correction (FEC) is enabled on a port and the
                port is online
           -1 : Not Applicable when received as response for GET operation

          FEC is supported in only at 10GB and 16GB speeds.
          ";
      }
      leaf via-tts-fec-enabled {
        type int8 {
          range "-1|0..1";
        }
        config false;
        description
          "
          FEC negotiation via TTS feature is enabled.

             0 : The external control of FEC is disabled
             1 : The control of the Forward Error Correction (FEC) state is
                 permitted via TTS by an externally attached host or device
            -1 : Not Applicable when received as response for GET operation
          ";
      }
      leaf port-autodisable-enabled {
        type uint8 {
          range "0..1";
        }
        default "0";
        description
          "
          This resource causes the interface to become disabled when it
          encounters an event that would cause it to reinitialize.

          The port auto-disable resource minimizes traffic disruption introduced
          in some instances of automatic port recovery.

          When the auto-disable flag is set, you can specify the conditions that
          will prevent the port to reinitialize. Such conditions include loss of
          sync, loss of signal, OLS, NOS, and LIP. Note that a link reset does
          not cause a port auto-disable. When a port is in FICON Management
          Server (FMS) mode, an auto-disabled port remains persistently disabled
          across High Availability (HA) failover.

            0 : Disabled
            1 : Enabled
          ";
      }
      leaf rate-limit-enabled {
        if-feature fibrechannel:fibrechannel_switch_platform;
        type int16 {
          range "-1|0|200|400|600|800|1000|1500|2000|2500|3000|3500|4000|5000|7000|8000|9000|10000|11000|12000|13000|14000|15000|16000";
        }
        units "Mbps";
        default "0";
        description
          "
          This resource is applicable only to F/FL_Ports. For E/EX_Ports,
          this resource would not be effective. The ingress rate limit is
          enforced only when a given port can run at a speed higher than
          the speed specified in the configuration. Positive numeric values
          indicate a rate limit in Mbps.

            -1 : Not Applicable when received as response for GET operation
             0 : No rate limit set
          ";
      }
      leaf non-dfe-enabled {
        if-feature fibrechannel:fibrechannel_switch_platform;
        type uint8 {
          range "0..1";
        }
        default "0";
        description
          "
          Enables or disables non-DFE mode on the port.

          Active receiver DFE uses sophisticated algorithms to automatically
          adjust the receiver to compensate for signal distortions.

            0 : (Off) Automatic receiver adjustment through DFE is activated
            1 : (On) If the non-DFE enabled port is connected to a port that does
                not require fixed receiver equalization, CRC errors may be
                detected on the port and the link may toggle.

          Even if disabled, non-DFE is still automatically activated if both of
          following conditions are met if port speed is 8G or N8 and the
          fillword is IDLE.
          ";
      }
    }
    list fibrechannel-statistics {
      key "name";
      description
        "
        The statistics for the interfaces on the device.

        System-controlled interfaces created by the system are always present in
        this list, whether they are configured or not.
        ";
      leaf name {
        type string {
          /* pattern with 12 slots and 1024 ports seperated by a slash */
          pattern "(([1-9]|1[0-9])/([1][0-9][0-9][0-9]|[1-9][1-9][0-9]|[1-9][1-9]|[1-9]))";
        }
        description
          "
          The name of the interface; the slot and port number of the port
          (slot/port).
          ";
      }
      leaf sampling-interval {
        type uint16 {
          range "1..max";
        }
        units "seconds";
        config false;
        description
          "Sampling interval in seconds.";
      }
      leaf time-generated {
        type fibrechannel:time-generated-type;
        config false;
        description
          "The time at which the statistics were queried.";
      }
      leaf reset-statistics {
        type uint8 {
          range "0..1";
        }
        description
          "
          To reset statistical counters, reset-statistics should be set to 1.
          Zero is always returned during read operations.
          ";
      }
      leaf in-octets {
        type yang:zero-based-counter64;
        config false;
        description
          "
          The total number of octets received on the interface, including
          framing characters.
          ";
      }
      leaf out-octets {
        type yang:zero-based-counter64;
        config false;
        description
          "
          The total number of octets transmitted out of the interface, including
          framing characters.
          ";
      }
      leaf in-multicast-pkts {
        type yang:zero-based-counter64;
        config false;
        description
          "
          The number of packets, delivered by this sub-layer to a higher
          (sub-)layer, that were addressed to a multicast address at this
          sub-layer.  For a MAC-layer protocol, this includes both Group and
          Functional addresses.
          ";
      }
      leaf out-multicast-pkts {
        type yang:zero-based-counter64;
        config false;
        description
          "
          The total number of packets that higher-level protocols requested be
          transmitted, and that were addressed to a multicast address at this
          sub-layer, including those that were discarded or not sent. For a
          MAC-layer protocol, this includes both Group and Functional addresses.
          ";
      }
      leaf in-link-resets {
        type yang:zero-based-counter64;
        config false;
        description
          "The number of link resets received.";
      }
      leaf out-link-resets {
        type yang:zero-based-counter64;
        config false;
        description
          "The total number of Link resets transmitted.";
      }
      leaf in-offline-sequences {
        type yang:zero-based-counter64;
        config false;
        description
          "The total number of offline sequences received.";
      }
      leaf out-offline-sequences {
        type yang:zero-based-counter64;
        config false;
        description
          "The total number of offline sequences transmitted.";
      }
      leaf invalid-ordered-sets {
        type yang:zero-based-counter64;
        config false;
        description
          "The total number of invalid ordered sets received.";
      }
      leaf frames-too-long {
        type yang:zero-based-counter64;
        config false;
        description
          "
          The number of frames received that were longer than 2140 octets. The
          value of 2140 is calculated based on an assumption of 24 header bytes
          plus 4 CRC bytes and 2112 bytes of payload.
          ";
      }
      leaf truncated-frames {
        type yang:zero-based-counter64;
        config false;
        description
          "The total number of truncated frames received.";
      }
      leaf address-errors {
        type yang:zero-based-counter64;
        config false;
        description
          "
          Count of frames received with unknown addressing. An example is an
          unknown SID or DID. The SID or DID is not known to the routing
          algorithm.
          ";
      }
      leaf delimiter-errors {
        type yang:zero-based-counter64;
        config false;
        description
          "
          Count of invalid frame delimiters that are received at this port. An
          example is a frame with a class 2 start and a class 3 at the end.
          ";
      }
      leaf encoding-disparity-errors {
        type yang:zero-based-counter64;
        config false;
        description
          "The total number of disparity errors received at this port.";
      }
      leaf too-many-rdys {
        type yang:zero-based-counter64;
        config false;
        description
          "The number of times RDYs exceed frames received.";
      }
      leaf in-crc-errors {
        type yang:zero-based-counter64;
        config false;
        description
          "The number of CRC errors for all frames received.";
      }
      leaf crc-errors {
        type yang:zero-based-counter64;
        config false;
        description
          "
          Number of times that the CRC in a frame does not match the CRC that is
          computed by the receiver. This count is part of the Link Error Status
          Block (LESB).
          ";
      }
      leaf bad-eofs-received {
        type yang:zero-based-counter64;
        config false;
        description
          "The number of bad EOF frames received.";
      }
      leaf encoding-errors-outside-frame {
        type yang:zero-based-counter64;
        config false;
        description
          "
          The number of encoding error or disparity error outside frames
          received.
          ";
      }
      leaf multicast-timeouts {
        type yang:zero-based-counter64;
        config false;
        description
          "The number of multicast frames that have timed out.";
      }
      leaf in-lcs {
        type yang:zero-based-counter64;
        config false;
        description
          "The number of link control frames received.";
      }
      leaf in-frame-rate {
        type yang:zero-based-counter64;
        config false;
        description
          "The instantaneous receive frame rate.";
      }
      leaf out-frame-rate {
        type yang:zero-based-counter64;
        config false;
        description
          "The instantaneous transmit frame rate.";
      }
      leaf in-max-frame-rate {
        type yang:zero-based-counter64;
        config false;
        description
          "The maximum frame receive rate since last reset.";
      }
      leaf out-max-frame-rate {
        type yang:zero-based-counter64;
        config false;
        description
          "The maximum frame transmit rate since last reset.";
      }
      leaf in-rate {
        type yang:zero-based-counter64;
        config false;
        description
          "The instantaneous byte receive rate.";
      }
      leaf out-rate {
        type yang:zero-based-counter64;
        config false;
        description
          "The instantaneous byte transmit rate.";
      }
      leaf in-peak-rate {
        type yang:zero-based-counter64;
        config false;
        description
          "The peak byte receive rate.";
      }
      leaf out-peak-rate {
        type yang:zero-based-counter64;
        config false;
        description
          "The peak byte transmit rate.";
      }
      leaf in-frames {
        type yang:zero-based-counter64;
        config false;
        description
          "Number of frames received.";
      }
      leaf out-frames {
        type yang:zero-based-counter64;
        config false;
        description
          "Number of frames transmitted.";
      }
      leaf bb-credit-zero {
        type yang:zero-based-counter64;
        config false;
        description
          "The number of transitions in and out of BB-Credit zero state";
      }
      leaf input-buffer-full {
        type yang:zero-based-counter64;
        config false;
        description
          "The number of transitions in and out of Input Buffer Full state.";
      }
      leaf f-busy-frames {
        type yang:zero-based-counter64;
        config false;
        description
          "The number of F_BSY frames generated.";
      }
      leaf p-busy-frames {
        type yang:zero-based-counter64;
        config false;
        description
          "Number of P_BSY frames generated.";
      }
      leaf f-rjt-frames {
        type yang:zero-based-counter64;
        config false;
        description
          "Number of F_RJT frames generated.";
      }
      leaf p-rjt-frames {
        type yang:zero-based-counter64;
        config false;
        description
          "Number of P_RJT frames generated.";
      }
      leaf class-1-frames {
        type yang:zero-based-counter64;
        config false;
        description
          "Number of Class 1 frames received";
      }
      leaf class-2-frames {
        type yang:zero-based-counter64;
        config false;
        description
          "Number of Class 2 frames received";
      }
      leaf class-3-frames {
        type yang:zero-based-counter64;
        config false;
        description
          "Number of Class 3 frames received";
      }
      leaf class-3-discards {
        type yang:zero-based-counter64;
        config false;
        description
          "Number of Class 3 frames discarded by the port.";
      }
      leaf link-failures {
        type yang:zero-based-counter64;
        config false;
        description
          "Number of link failures.";
      }
      leaf invalid-transmission-words {
        type yang:zero-based-counter64;
        config false;
        description
          "Number of invalid transmission words received.";
      }
      leaf primitive-sequence-protocol-error {
        type yang:zero-based-counter64;
        config false;
        description
          "Number of primitive sequence protocol errors detected at this port.";
      }
      leaf loss-of-signal {
        type yang:zero-based-counter64;
        config false;
        description
          "Number of instances of signal loss detected at this port.";
      }
      leaf loss-of-sync {
        type yang:zero-based-counter64;
        config false;
        description
          "Number of instances of synchronization loss detected at this port.";
      }
      leaf class3-in-discards {
        type yang:zero-based-counter64;
        config false;
        description
          "Number of C3 receive frames discarded due to timeout";
      }
      leaf class3-out-discards {
        type yang:zero-based-counter64;
        config false;
        description
          "Number of C3 transmit frames discarded due to timeout";
      }
      leaf pcs-block-errors {
        type yang:zero-based-counter64;
        config false;
        description
          "
          The number of Physical Coding Sublayer (PCS) block errors. This
          counter records encoding violations on 10 Gbps or 16 Gbps ports.
          ";
      }
    }
  }
}
